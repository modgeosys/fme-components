FME workspace ProcessCustomOAuth2Callback.fmwt
Title: ProcessCustomOAuth2Callback
Description: Generate an OAuth2 callback endpoint workspace.
Usage: To use this template, simply:
    Open the template file and save it as a workspace; 
    Modify it to suit your needs, most likely by changing the file names and paths in the private parameters.

Parameters:
- code =   # Authorization Code
- Data_Directory = $(FME_SHAREDRESOURCE_DATA)   # Data Directory
- Configuration_Filename = Custom_APIConfiguration.json   # Configuration Filename
- DestDataset_HTML = $(FME_SHAREDRESOURCE_DATA)/Output/ProcessCustomOAuth2Callback.html   # HTML Files(*.html)|*.html Destination Html File
- FME_SHAREDRESOURCE_DATA = $(FME_MF_DIR)2/Resources/Data   # FME Server Resource Data

Writers:
- HTML_1: HTML to $(DestDataset_HTML)

Creator
    GEOMTYPE = Geometry Object
    NUM = 1
    CREATED -> ParameterFetcher
ParameterFetcher
    ATTR_LIST = oauth2_code $(code)
    -> ParameterAttributeCreator
ParameterAttributeCreator: AttributeCreator
    ATTR_TABLE:
      SET_TO oauth2_data_directory = $(Data_Directory)
      SET_TO oauth2_configuration_filename = $(Configuration_Filename)
    -> OAuth2CallbackProcessor
OAuth2CallbackProcessor
    OAUTH2_CODE = @Value(oauth2_code)
    OAUTH2_CONFIGURATION_FILENAME = @Value(oauth2_configuration_filename)
    OAUTH2_DATA_DIRECTORY = @Value(oauth2_data_directory)
    -> SuccessAttributeCreator
    <Rejected>Output -> FailureAttributeCreator
SuccessAttributeCreator: AttributeCreator
    ATTR_TABLE:
      SET_TO html_content = <html>
            <head>
                <title>Authorized</title>
            <head>
            <body>
                You are now authorized.
            </body>
         </html>
    -> HTML (writer HTML_1)
FailureAttributeCreator: AttributeCreator
    ATTR_TABLE:
      SET_TO html_content = <html>
            <head>
                <title>Authorized</title>
            <head>
            <body>
                You are unauthorized:  @Value(oauth2_error)
                @Value(oauth2_response_body)
            </body>
         </html>
    -> HTML (writer HTML_1)
HTML (writer HTML_1)
    attributes: html_content buffer
