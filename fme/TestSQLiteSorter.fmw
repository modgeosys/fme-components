FME workspace TestSQLiteSorter.fmw
Title: TestSQLiteSorter
Description: Test SQLiteSorter output against Sorter output.
For issues or questions, please Create an issue here.  For the source, including test driver components, please see the Github repository.
Copyright © 2017-2019 by Modern geoSystems, released under this BSD 3-clause license.
History: 2018-03-08,Kevin Weller,Updates to reflect move from GitHub to Assembla and Atlassian.,2019-05-09,Kevin Weller,Update  to FME 2018.1.2.1 and use new AttributeValidation* test framework.

Parameters:
- Sort_Keys:   # " " Sort Keys
      kml_name		varchar	asc
      kml_id			varchar	desc
- SourceDataset_OGCKML = https://github.com/modgeosys/fme-components/blob/master/fme/Resources/Data/Test/USGS_DS_817_truncated.kmz?raw=true   # Source Google KML File or URL
- DestDataset_HTML = $(FME_MF_DIR)Resources/Data/Output/TestSQLiteSorter.html   # HTML Files(*.html)|*.html Destination Html File
- FEATURE_TYPES =
- FME_SHAREDRESOURCE_DATA = $(FME_MF_DIR_USERTYPED)/Resources/Data   # FME Server Resource Data

Readers:
- OGCKML_1: OGCKML from $(SourceDataset_OGCKML)

Writers:
- HTML_1: HTML to $(DestDataset_HTML)

AnimatedUpdate (reader OGCKML_1)
    -> AttributeExposer
Note: Expose sort key / attributes in test / input dataset.
AttributeExposer
    ATTR_LIST = kml_id,kml_name
    -> Sorter
    -> SQLiteSorter
SortOrderAttributeValidator: AttributeValidator
    TABLE = sort_order_matches;IN;TRUE
    PASSED -> SortOrderAttributeValidationListPopulator
    FAILED -> SortOrderAttributeValidationListPopulator
SortOrderAttributeValidationListPopulator: AttributeValidationListPopulator
    Validator_Name = SortOrder
    -> AttributeValidationHTMLReportGenerator
Note: Make sure the features / themselves are not / altered by the process.
ChangeDetector
    BLANK_AND_MISSING_DIFFER = Yes
    LENIENT_MATCH = No
    MATCH = FULL
    MATCHATTRS = kml_name kml_id
    MATCH_STRATEGY = Match All Except Selected Attributes
    UNCHANGED -> SortFeatureUnchangedAttributeCreator
    ADDED -> SortFeatureAddedAttributeCreator
    DELETED -> SortFeatureDeletedAttributeCreator
SortFeatureUnchangedAttributeCreator: AttributeCreator
    ATTR_TABLE = SET_TO unmatched_sort_feature = UNCHANGED
    -> SortFeatureChangeAttributeValidator
SortFeatureAddedAttributeCreator: AttributeCreator
    ATTR_TABLE = SET_TO unmatched_sort_feature = ADDED
    -> SortFeatureChangeAttributeValidator
SortFeatureDeletedAttributeCreator: AttributeCreator
    ATTR_TABLE = SET_TO unmatched_sort_feature = DELETED
    -> SortFeatureChangeAttributeValidator
SortFeatureChangeAttributeValidator: AttributeValidator
    TABLE = unmatched_sort_feature;IN;UNCHANGED
    PASSED -> SortFeatureChangeAttributeValidationListPopulator
    FAILED -> SortFeatureChangeSorter
SortFeatureChangeSorter: Sorter
    SORT_PARM = kml_id ALPHA ASCENDING unmatched_sort_feature ALPHA ASCENDING
    SORTED -> SortFeatureChangeAttributeValidationListPopulator
SortFeatureChangeAttributeValidationListPopulator: AttributeValidationListPopulator
    Validator_Name = SortFeatureChange
    -> AttributeValidationHTMLReportGenerator
AttributeValidationHTMLReportGenerator
    _FEATURE_ID = FME_CONDITIONAL:DEFAULT_VALUE''BOOL_OP;OR;COMPOSITE_TEST;<Unused>;TEST kml_id ATTRIBUTE_HAS_A_VALUE _FME_BLANK_STRING_'@Value(kml_id) - @Value(kml_name)'FME_NUM_CONDITIONS2___
    -> HTML (writer HTML_1)
HTML (writer HTML_1)
    attributes: html_content buffer

Bookmark: Sort using standard Sorter for comparison with SQLiteSorter results.
Sorter
    SORT_PARM = kml_name ALPHA ASCENDING kml_id ALPHA DESCENDING
    SORTED -> ChangeDetector [ORIGINAL]
    SORTED -> SorterFeatureWriter [Sorted]
SorterFeatureWriter: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)/Output
    DATASET_ATTR = _dataset
    FEATURE_TYPE_LIST_ATTR = _feature_type
    FORMAT = CSV2
    TOTAL_FEATURES_WRITTEN_ATTR = _total_features_written
    SUMMARY -> SorterDatasetAttributeRenamer
SorterDatasetAttributeRenamer: AttributeRenamer
    ATTR_TABLE = RENAME_SET_DEFAULT _dataset > sorter_dataset
    -> FeatureMerger [REQUESTOR]

Bookmark: Sort using SQLiteSorter.
SQLiteSorter
    Sort_Keys = $(Sort_Keys)
    Sorted -> ChangeDetector [REVISED]
    Sorted -> SQLiteSorterFeatureWriter [File1]
SQLiteSorterFeatureWriter: FeatureWriter
    CSV2_COORDINATE_SYSTEM_GRANULARITY = FEATURE_TYPE
    CSV2_DELIMITER = ,
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_WRITE_BOM_FOR_UNICODE = Yes
    CSV2_WRITE_FIELD_NAMES = firstrow
    CSV2_WRITE_SCHEMA_FILE = NO
    DATASET = $(FME_SHAREDRESOURCE_DATA)/Output
    DATASET_ATTR = _dataset
    FEATURE_TYPE_LIST_ATTR = _feature_type
    FORMAT = CSV2
    TOTAL_FEATURES_WRITTEN_ATTR = _total_features_written
    SUMMARY -> SQLiteSorterDatasetAttributeRenamer
SQLiteSorterDatasetAttributeRenamer: AttributeRenamer
    ATTR_TABLE = RENAME_SET_DEFAULT _dataset > sqlite_sorter_dataset
    -> FeatureMerger [SUPPLIER]

Bookmark: Compare sort order.
Note: Synchronize on sort / CSV output writer / summary features / by merging them.
FeatureMerger
    ATTR_ACCUM_MODE = Merge Supplier
    ATTR_CONFLICT_RES = Use Requestor
    CLEANING_TOLERANCE = None
    IGNORE_NULLS = No
    JOIN_KEYS = @Value(_total_features_written) @Value(_total_features_written) AUTO
    MERGE_TYPE = Attributes Only
    PROCESS_DUPS = No
    REJECT_NULL_MISSING_KEYS = No
    SUPPLIERS_FIRST = No
    MERGED -> DiffSystemCaller
    <REJECTED> -> NullDiffAttributeCreator
Note: Compare the CSVs to / check for same sort order.
DiffSystemCaller: SystemCaller
    ATTR = comparison_result
    CMD = diff @Value(sorter_dataset) @Value(sqlite_sorter_dataset)
    -> ComparisonResultAttributeFilter
Note: Feature counts don't match.
NullDiffAttributeCreator: AttributeCreator
    ATTR_TABLE = SET_TO comparison_result = FME_NULL_VALUE
    -> ComparisonResultAttributeFilter
ComparisonResultAttributeFilter: AttributeFilter
    ATTR_NAME = comparison_result
    ATTR_VALUES = 0,<Empty>,<Missing>,<Null>,<Unfiltered>
    0 -> SortOrderSameAttributeCreator
    <EMPTY> -> SortOrderDifferentAttributeCreator
    <MISSING> -> SortOrderDifferentAttributeCreator
    <NULL> -> SortOrderDifferentAttributeCreator
    <UNFILTERED> -> SortOrderDifferentAttributeCreator
SortOrderSameAttributeCreator: AttributeCreator
    ATTR_TABLE = SET_TO sort_order_matches = TRUE
    -> SortOrderAttributeValidator
SortOrderDifferentAttributeCreator: AttributeCreator
    ATTR_TABLE = SET_TO sort_order_matches = FALSE
    -> SortOrderAttributeValidator

FME custom transformer AttributeValidationListPopulator

Parameters:
- Validator_Name =   # Validator Name

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer AttributeValidationHTMLReportGenerator

Parameters:
- _FEATURE_ID = @Value(_feature_id)   # Feature ID

input (input)
    -> PythonCaller
PythonCaller
    NEW_ATTRIBUTES = _mgs_validation_message _mgs_validator_name _mgs_calling_module
    PYTHONSOURCE:
      import fme
      import fmeobjects

      class FeatureProcessor(object):
          def __init__(self):
              pass

          def input(self,feature):
              messages = feature.getAttribute('_fme_validation_message_list')
              if messages:
                  attribute_names = feature.getAllAttributeNames()
                  index = 0
                  for message in messages:
                      exploded_feature = feature.clone()
                      exploded_feature.setAttribute('_mgs_validation_message', feature.getAttribute('_fme_validation_message_list{' + str(index) + '}'))
                      exploded_feature.setAttribute('_mgs_validator_name', feature.getAttribute('_fme_validation_message_list{' + str(index) + '}.validator_name'))
                      exploded_feature.setAttribute('_mgs_calling_module', feature.getAttribute('_fme_validation_message_list{' + str(index) + '}.calling_module'))
                      exploded_feature.removeAttribute('_fme_validation_message_list{}')
                      exploded_feature.removeAttribute('_fme_validation_message_list{}.validator_name')
                      exploded_feature.removeAttribute('_fme_validation_message_list{}.calling_module')
                      self.pyoutput(exploded_feature)
                      index += 1

          def close(self):
              pass
    PYTHONSYMBOL = FeatureProcessor
    -> NoFeaturesTester
NoFeaturesTester
    NOINPUT -> HTMLReportGenerator
    -> HTMLReportGenerator
HTMLReportGenerator
    CONTENT_LIST = HEADER HTML TABLE
    GROUP_BY = _mgs_calling_module
    PAGE_CONFIG:
      HEADER{{TEXT;Module: @Value(_mgs_calling_module);HEADER;H4;ALIGNMENT;LEFT;COLOR;0,0,0;FME_CONTROLLER_QUERY_FILE;transformers/dependencies/html5/Header.fme}}HTML{{HTML;<div>
          <ul>
              <li>FME Build Number: $(FME_BUILD_NUM)</li>
              <li>FME Build Date: $(FME_BUILD_DATE)
              <li>FME Home: $(FME_HOME_UNIX_USERTYPED)</li>
              <li>FME Product Name: $(FME_PRODUCT_NAME)
          </ul>
      </div>;FME_CONTROLLER_QUERY_FILE;transformers/dependencies/html5/Custom HTML.fme}}TABLE{{STYLE;STRIPED;TABLE;_feature_id|Feature ID/_mgs_validator_name|Validator/_mgs_validation_message|Message;FME_CONTROLLER_QUERY_FILE;transformers/dependencies/html5/Table.fme}}
    TITLE = Test Results for Workspace: $(WORKSPACE_NAME)
    -> Output (output)
Output (output)

FME custom transformer NoFeaturesTester
This transformer checks whether there are any input features. If not, then a single feature is ouput via the NOINPUT port. If INPUT features exist, then they are output via the INPUT output port.
Other transformers often generate features that signify an error condition. This transformer can be used to check for those features and if those features exists, then a separate action can be triggered.
    Example
This may be useful to test if any data emerges from a reader, when the 'Ignore Failed Readers' advanced parameter is set to yes.
Input Ports
    Input
Features to be checked for existence
    Output Ports
    NoInput
If no Input features exist, a single featue is returned via the NoInput port
    Output
Any feature that entered the Input port is returned via the Output port

INPUT (input)
    -> Sampler
    -> OUTPUT (output)
OUTPUT (output)
Sampler
    RATE = 1
    SAMPLE_MODE = No
    SAMPLE_TYPE_LONG = First N Features
    SAMPLED -> AttributeCreator_2
AttributeCreator_2
    ATTR_TABLE:
      SET_TO count = 0
      SET_TO remove = yes
    -> DuplicateFilter
Creator
    GEOMTYPE = Geometry Object
    NUM = 1
    CREATED -> AttributeCreator_3
AttributeCreator_3
    ATTR_TABLE = SET_TO no_features = true
    -> DuplicateFilter
DuplicateFilter
    INPUT_ORDERED_CHOICE = No
    KEYATTR = count
    UNIQUE -> Tester
Tester
    BOOL_OP = OR
    TEST_CLAUSE = TEST @Value(remove) != yes
    TEST_MODE = TEST
    PASSED -> AttributeRemover
AttributeRemover
    REMOVE_ATTRS = count,remove
    -> NOINPUT (output)
NOINPUT (output)
