FME workspace TestGeometryValidationHTMLReportGenerator.fmw

Parameters:
- DestDataset_HTML = $(FME_MF_DIR)Resources/Temp/GeometryValidationHTMLReportGeneratorTestOutput.html   # Destination Html File

Writers:
- HTML_1: HTML to $(DestDataset_HTML)

Note: Validate feature geometries.
GeometryValidator
    ISSUE_ATTR_NAME = _issues
    PRESETS = All
    REPAIR = Yes
    RULES = AREA_ORIENTATION AREA_ORIENTATION]VALID]FME_CONTROLLER_QUERY_FILE]transformers/dependencies/geometryvalidator8/AREA_ORIENTATION.fme]FME_CONTROLLER_CHOICE]AREA_ORIENTATION CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D MISSING_TEXTURE_COORDINATES FME_CONTROLLER_QUERY_FILE]transformers/dependencies/geometryvalidator/MISSING_TEXTURE_COORDINATES.fme]FME_CONTROLLER_CHOICE]MISSING_TEXTURE_COORDINATES MISSING_VERTEX_NORMALS FME_CONTROLLER_QUERY_FILE]transformers/dependencies/geometryvalidator/MISSING_VERTEX_NORMALS.fme]FME_CONTROLLER_CHOICE]MISSING_VERTEX_NORMALS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator/NULL_REMOVAL.fme]FME_CONTROLLER_CHOICE]NULL_REMOVAL OGC_SIMPLE_CHECK LEGACY_OGC]No]FME_CONTROLLER_QUERY_FILE]transformers/dependencies/geometryvalidator8/OGC_SIMPLE_CHECK.fme]FME_CONTROLLER_CHOICE]OGC_SIMPLE_CHECK OGC_VALID_CHECK OGC_VERSION]V1.2.0]LEGACY_OGC]No]FME_CONTROLLER_QUERY_FILE]transformers/dependencies/geometryvalidator8/OGC_VALID_CHECK.fme]FME_CONTROLLER_CHOICE]OGC_VALID_CHECK PLANAR_SURFACE CHECK_AREA]DO_NOT_CHECK_AREA]TOLERANCE_MODE]AUTO]TOLERANCE]<Unused>]ANGULAR_TOLERANCE_MODE]AUTO]ANGULAR_TOLERANCE]<Unused>]FME_CONTROLLER_QUERY_FILE]transformers/dependencies/geometryvalidator8/PLANAR_SURFACE.fme]FME_CONTROLLER_CHOICE]PLANAR_SURFACE SELF_INTERSECTING CHECK_HOLE_TOUCHING_POLYGON]No]CONNECT_Z_MODE_SI]FIRST_WINS]SELF_INTERSECTION_TOLERANCE]None]INTERSECT_ACROSS_MULTIS]No]FME_CONTROLLER_QUERY_FILE]transformers/dependencies/geometryvalidator8/SELF_INTERSECTING.fme]FME_CONTROLLER_CHOICE]SELF_INTERSECTING SHELL_VALIDATION FLIP_APPEARANCE_MODE]FLIP_APPEARANCES]FME_CONTROLLER_QUERY_FILE]transformers/dependencies/geometryvalidator8/SHELL_VALIDATION.fme]FME_CONTROLLER_CHOICE]SHELL_VALIDATION SOLID_VOID_REPAIR FME_CONTROLLER_QUERY_FILE]transformers/dependencies/geometryvalidator/SOLID_VOID_REPAIR.fme]FME_CONTROLLER_CHOICE]SOLID_VOID_REPAIR TYPE_REPAIR CONNECT_Z_MODE]FIRST_WINS]ARC_ENDPOINT_TOLERANCE_MODE]Auto]ARC_ENDPOINT_TOLERANCE]<Unused>]FME_CONTROLLER_QUERY_FILE]transformers/dependencies/geometryvalidator8/TYPE_REPAIR.fme]FME_CONTROLLER_CHOICE]TYPE_REPAIR MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS MISSING_MEASURES_AND_ELEVATIONS MISSING_VALUES_MODE]SENTINEL]MISSING_MEASURES_MODE]<Unused>]SENTINEL_VALUE]0]LENGTH_DIMENSION]<Unused>]FME_CONTROLLER_QUERY_FILE]transformers/dependencies/geometryvalidator8/MISSING_MEASURES_AND_ELEVATIONS.fme]FME_CONTROLLER_CHOICE]MISSING_MEASURES_AND_ELEVATIONS SURFACE_ORIENTATION FME_CONTROLLER_QUERY_FILE]transformers/dependencies/geometryvalidator/SURFACE_ORIENTATION.fme]FME_CONTROLLER_CHOICE]SURFACE_ORIENTATION SOLID_ORIENTATION FME_CONTROLLER_QUERY_FILE]transformers/dependencies/geometryvalidator/SOLID_ORIENTATION.fme]FME_CONTROLLER_CHOICE]SOLID_ORIENTATION
    SUMMARY = Detailed
    FAILED -> GeometryValidationHTMLReporter [Failed]
    REPAIRED -> GeometryValidationHTMLReporter [Repaired]
Note: Generate the geometry validation results report.
GeometryValidationHTMLReporter
    _FEATURE_ID = @Value(_feature_id)
    Report -> HTML (writer HTML_1)
Note: HTML: GeometryValidationHTMLReportGeneratorTestOutput [HTML]
HTML (writer HTML_1)
    attributes: html_content buffer

Bookmark: Test cases.
Creator_20
    GEOMTYPE = Geometry Object
    NUM = 1
    CREATED -> AttributeCreator_20
Note: Self Intersecting donut
AttributeCreator_20
    ATTR_LIST = _geometry,POLYGON((2 2, 8 8, 2 8, 8 2, 2 2)),Fail_reason,Self Intersecting donut
    -> GeometryReplacer
Creator_19
    GEOMTYPE = Geometry Object
    NUM = 1
    CREATED -> AttributeCreator_19
Note: Self Intersecting donut
AttributeCreator_19
    ATTR_LIST = _geometry,POLYGON((0 0, 10 0, 10 10, 0 10, 0 0), (2 2, 8 8, 2 8, 8 2, 2 2)),Fail_reason,Self Intersecting donut
    -> GeometryReplacer
Creator_18
    GEOMTYPE = Geometry Object
    NUM = 1
    CREATED -> AttributeCreator_18
Note: Closed snake
AttributeCreator_18
    ATTR_LIST = _geometry,POLYGON((0 0,6 0,6 8,1 8,1 7,5 7,5 1,1 1,1 8,0 8,0 0)),Fail_reason,closed snake
    -> GeometryReplacer
Creator_17
    GEOMTYPE = Geometry Object
    NUM = 1
    CREATED -> AttributeCreator_17
Note: Closed U
AttributeCreator_17
    ATTR_LIST = _geometry,POLYGON((0 0,6 0,6 8,5 8,5 6,2 6,2 8,6 8,0 8,0 0)),Fail_reason,closed U
    -> GeometryReplacer
Creator_16
    GEOMTYPE = Geometry Object
    NUM = 1
    CREATED -> AttributeCreator_16
Note: Sliver
AttributeCreator_16
    ATTR_LIST = _geometry,POLYGON((0 0,6 0,4 0.001,0 0)),Fail_reason,Sliver
    -> GeometryReplacer
Creator_9
    GEOMTYPE = Geometry Object
    NUM = 1
    CREATED -> AttributeCreator_9
Note: Invalid Coordinates
AttributeCreator_9
    ATTR_LIST = _geometry,POLYGON((NaN 3, 3 4, 4 4, 4 3, 3 3)),Fail_reason,Invalid Coordinates
    -> GeometryReplacer
Creator_15
    GEOMTYPE = Geometry Object
    NUM = 1
    CREATED -> AttributeCreator_15
Note: Multi without part
AttributeCreator_15
    ATTR_LIST = _geometry,MULTIPOLYGON(((1 1,5 1,5 5,1 5,1 1),(2 2,2 3,3 3,3 2,2 2))),Fail_reason,Multi without part
    -> GeometryReplacer
Creator_12
    GEOMTYPE = Geometry Object
    NUM = 1
    CREATED -> AttributeCreator_11
Note: Donut Without Holes
AttributeCreator_11
    ATTR_LIST = _geometry,POLYGON((0 0, 10 0, 10 10, 0 10, 0 0), (2 2, 2 9)),Fail_reason,Donut wihtout Hole
    -> GeometryReplacer
Creator_13
    GEOMTYPE = Geometry Object
    NUM = 1
    CREATED -> AttributeCreator_13
Note: Multi with selfIntersect
AttributeCreator_13
    ATTR_LIST = _geometry,MULTIPOLYGON(((1 1,5 1,5 5,1 5,1 1),(2 2,2 3,3 3,3 2,2 2)),((0 0, 10 10, 0 10, 10 0, 0 0))),Fail_reason,Multi with selfIntersect
    -> GeometryReplacer
Creator_14
    GEOMTYPE = Geometry Object
    NUM = 1
    CREATED -> AttributeCreator_14
Note: Multi with corrupt part
AttributeCreator_14
    ATTR_LIST = _geometry,MULTIPOLYGON(((1 1,5 1,5 5,1 5,1 1),(2 2,2 3,3 3,3 2,2 2)),((0 0, 10 10))),Fail_reason,Multi with corrupt Part
    -> GeometryReplacer
Creator
    GEOMTYPE = Geometry Object
    NUM = 1
    CREATED -> AttributeCreator
Note: HOLE outside shell
AttributeCreator
    ATTR_LIST = _geometry,POLYGON((0 0, 10 0, 10 10, 0 10, 0 0), (15 15, 15 20, 20 20, 20 15, 15 15)),Fail_reason,HOLE outside shell
    -> GeometryReplacer
Creator_2
    GEOMTYPE = Geometry Object
    NUM = 1
    CREATED -> AttributeCreator_2
Note: Nested Holes
AttributeCreator_2
    ATTR_LIST = _geometry,POLYGON((0 0, 10 0, 10 10, 0 10, 0 0), (2 2, 2 8, 8 8, 8 2, 2 2), (3 3, 3 7, 7 7, 7 3, 3 3)),Fail_reason,Nested Holes
    -> GeometryReplacer
Creator_3
    GEOMTYPE = Geometry Object
    NUM = 1
    CREATED -> AttributeCreator_3
Note: Disconnected Interior
AttributeCreator_3
    ATTR_LIST = _geometry,POLYGON((0 0, 10 0, 10 10, 0 10, 0 0), (5 0, 10 5, 5 10, 0 5, 5 0)),Fail_reason,Disconnected Interior
    -> GeometryReplacer
Creator_4
    GEOMTYPE = Geometry Object
    NUM = 1
    CREATED -> AttributeCreator_4
Note: Self Intersection
AttributeCreator_4
    ATTR_LIST = _geometry,POLYGON((0 0, 10 10, 0 10, 10 0, 0 0)),Fail_reason,Self Intersection
    -> GeometryReplacer
Creator_5
    GEOMTYPE = Geometry Object
    NUM = 1
    CREATED -> AttributeCreator_5
Note: Ring Self Intersection
AttributeCreator_5
    ATTR_LIST = _geometry,POLYGON((5 0, 10 0, 10 10, 0 10, 0 0, 5 0, 3 3, 5 6, 7 3, 5 0)),Fail_reason,Ring Self Intersection
    -> GeometryReplacer
Creator_6
    GEOMTYPE = Geometry Object
    NUM = 1
    CREATED -> AttributeCreator_6
Note: Nested Shell
AttributeCreator_6
    ATTR_LIST = _geometry,MULTIPOLYGON(((0 0, 10 0, 10 10, 0 10, 0 0)),(( 2 2, 8 2, 8 8, 2 8, 2 2))),Fail_reason,Nested Shell
    -> GeometryReplacer
Creator_7
    GEOMTYPE = Geometry Object
    NUM = 1
    CREATED -> AttributeCreator_7
Note: Duplicated Rings
AttributeCreator_7
    ATTR_LIST = _geometry,MULTIPOLYGON(((0 0, 10 0, 10 10, 0 10, 0 0)),((0 0, 10 0, 10 10, 0 10, 0 0))),Fail_reason,Duplicated Rings
    -> GeometryReplacer
Creator_8
    GEOMTYPE = Geometry Object
    NUM = 1
    CREATED -> AttributeCreator_8
Note: Too Few Points
AttributeCreator_8
    ATTR_LIST = _geometry,POLYGON((2 2, 8 2)),Fail_reason,Too Few Points
    -> GeometryReplacer
Creator_10
    GEOMTYPE = Geometry Object
    NUM = 1
    CREATED -> AttributeCreator_10
Note: Ring Not Closed
AttributeCreator_10
    ATTR_LIST = _geometry,POLYGON((0 0, 0 10, 10 10, 10 0)),Fail_reason,Ring Not Closed
    -> GeometryReplacer
Creator_11
    GEOMTYPE = Geometry Object
    NUM = 1
    CREATED -> AttributeCreator_12
Note: Duplicated Point
AttributeCreator_12
    ATTR_LIST = _geometry,POLYGON((0 0, 0 10, 10 10, 10 10, 10 0, 0 0)),Fail_reason,Duplicated Point
    -> GeometryReplacer

Bookmark: Prepare test features for geometry validation.
Note: Create native geometry from OGC WKT.
GeometryReplacer
    ATTR = _geometry
    KIND_LONG = OGC Well Known Text
    -> Counter
Note: Generate test feature ID.
Counter
    CNT_ATTR = _feature_id
    DOMAIN = counter
    SCOPE = Global
    START = 0
    -> Offsetter
Note: Spatially separate test geometries.
Offsetter
    XOFF = 10*@Value(_feature_id)
    YOFF = 0
    ZOFF = 0
    OFFSET -> GeometryValidator
    OFFSET -> GeometryValidationHTMLReporter [Original]

FME custom transformer GeometryValidationHTMLReporter
Generate an HTML report detailing the complete results of a preceding GeometryValidator transformer.  Repaired, partially repaired and unrepaired geometries are reported.  The output report is grouped by the identifier attribute values of the original features.
The geometries themselves are rendered on the report, except for those that cannot be rendered, because they are either not currently supported for rendering or they are too broken (e.g. unbounded in one or more dimensions) to be meaningfully rendered.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2022 by Modern geoSystems, released under this BSD 3-clause license.
Ports
Original
Feed all the original unvalidated features here. These are needed for report grouping.
Failed
Feed all features here from the Failed output port of the preceding GeometryValidator.
Repaired
Feed all features here from the Repaired output port of the preceding GeometryValidator.
Report
A single ouput feature enhanced with the following attribute:
html_content{} - The resulting HTML report suitable for output
Output
All Failed or Repaired input features with their reported geometry issue lists will be output here.
Parameters
Specify the required yet unknown values to support reporting the issues generated by the preceding GeometryValidator.
ID
The name of the attribute containing identifying information for grouping the reported issues by the original features.

Parameters:
- _FEATURE_ID = @Value(_feature_id)   # Feature Id

Original (input)
    -> GeometryValidationCallerPopulator
Failed (input)
    -> GeometryValidationCallerPopulator
Repaired (input)
    -> GeometryValidationCallerPopulator
Note: Prepare the feature for reporting.
GeometryValidationCallerPopulator
    _FEATURE_ID = @Value(_feature_id)
    Original -> GeometryValidationHTMLReportGenerator [Original]
    Exceptions -> GeometryValidationHTMLReportGenerator [Exceptions]
    Exceptions -> Output (output)
Note: Generate the report.
GeometryValidationHTMLReportGenerator
    _FEATURE_ID = @Value(_feature_id)
    _MGS_CALLING_MODULE = @Value(_mgs_calling_module)
    Report -> Report (output)
Report (output)
Output (output)

FME custom transformer FileDeleter_5
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_4
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_3

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_2

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_4

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer GeometryValidationHTMLReportGenerator

Parameters:
- _FEATURE_ID = @Value(_feature_id)   # Feature Id
- _MGS_CALLING_MODULE = @Value(_mgs_calling_module)   # Mgs Calling Module

Original (input)
    -> HeaderSampler
    -> LabelFeatureAttributeManager
Note: Take only the first feature element as a placeholder for the report header.
HeaderSampler: Sampler
    GROUP_BY = _mgs_calling_module
    RATE = 1
    SAMPLE_MODE = No
    SAMPLE_TYPE_LONG = First N Features
    SAMPLED -> HeaderHTMLReportGenerator
Note: Prepare the feature subheading row with the feature ID label, and all other attributes blank.
LabelFeatureAttributeManager: AttributeManager
    ATTR_TABLE:
      SET_TO _feature_label = @Value(_feature_id)
      SET_TO _feature_issue_index = -1
      SET_TO _feature_issue_supplement_index = -1
      SET_TO _issue_count
      SET_TO _issue_issue_found
      SET_TO _issue_location.x
      SET_TO _issue_location.y
      SET_TO _issue_location.z
      SET_TO _issue_location_sample.x
      SET_TO _issue_location_sample.y
      SET_TO _issue_location_sample.z
      SET_TO _issue_repair_state
      SET_TO _issue_supplementary_info
      SET_TO _issue_supplement_count
      SET_TO _issue_supplement_details
      SET_TO _issue_supplement_location.x
      SET_TO _issue_supplement_location.y
      SET_TO _issue_supplement_location.z
      SET_TO _issue_supplement_location_sample.x
      SET_TO _issue_supplement_location_sample.y
      SET_TO _issue_supplement_location_sample.z
      SET_TO _issue_supplement_original_part_index
    -> IssueElementSorter_3
Exceptions (input)
    -> AttributeExposer
IssueElementSorter_3
    _FEATURE_ID = @Value(_feature_id)
    _FEATURE_ISSUE_INDEX = @Value(_feature_issue_index)
    _FEATURE_ISSUE_SUPPLEMENT_INDEX = @Value(_feature_issue_supplement_index)
    _MGS_CALLING_MODULE = @Value(_mgs_calling_module)
    Sorted -> BoundsExtractor
BoundsExtractor
    XMAX = _xmax
    XMIN = _xmin
    YMAX = _ymax
    YMIN = _ymin
    ZMAX = _zmax
    ZMIN = _zmin
    -> IDCounter
IDCounter: Counter
    CNT_ATTR = id
    SCOPE = Local
    START = 0
    -> Base64PNGRasterizer
Base64PNGRasterizer
    All_Attributes_to_Preserve:
      import fme
      import re


      # Initialize the grouping attribute list with all the existing attribute parameters and all internally-generated attributes.
      result = 'id _xmax _xmax_extent _xmin _xmin_extent _ymax _ymax_extent _ymin _ymin_extent _base64_geometry _number_of_columns _number_of_rows _saved_color _saved_fill_color _size_ratio _x _y fme_color fme_feature_type fme_fill_color fme_rotation fme_text_size fme_text_string _not_rendered_text_string'

      # Add any custom attributes specified in the transformer parameters.
      sample_user_parameter = next(name for name in FME_MacroValues.keys() if re.search(r'_(ID|_[XY]MAX|_[XY]MIN)', name) and not name.startswith('FME_'))
      parameter_prefix = '_'.join([component for component in sample_user_parameter.split('_') if len(component) > 0][0:-1])
      if len(fme.macroValues[parameter_prefix + '_Custom_Attributes_to_Preserve']) > 0:
          result += ' ' + fme.macroValues[parameter_prefix + '_Custom_Attributes_to_Preserve']

      return result
    Custom_Attributes_to_Preserve = _feature_id _feature_issue_index _feature_issue_supplement_index _feature_label _issue_count _issue_issue_found _issue_location.x _issue_location.y _issue_location.z _issue_location_sample.x _issue_location_sample.y _issue_location_sample.z _issue_repair_state _issue_supplement_count _issue_supplement_details _issue_supplement_location.x _issue_supplement_location.y _issue_supplement_location.z _issue_supplement_location_sample.x _issue_supplement_location_sample.y _issue_supplement_location_sample.z _issue_supplement_original_part_index _issue_supplementary_info _mgs_calling_module
    Default_Fill_Color = 1,1,1,0
    Default_Pen_Color = 0,0,0,1
    ID = @Value(id)
    Name = $(FME_MF_NAME)
    _XMAX = @Value(_xmax)
    _XMIN = @Value(_xmin)
    _YMAX = @Value(_ymax)
    _YMIN = @Value(_ymin)
    -> Sorter
Sorter
    SORT_PARM = _mgs_calling_module ALPHA ASCENDING id NUMERIC ASCENDING
    SORTED -> GeometryImageTagAttributeCreator
GeometryImageTagAttributeCreator: AttributeCreator
    ATTR_TABLE = SET_TO _geometry_image_tag = FME_CONDITIONAL:DEFAULT_VALUE'<img src="data:image/png;base64, @Value(_image_base64)" alt="Geometry" width="256"/>'BOOL_OP;OR;COMPOSITE_TEST;1;TEST _not_rendered_text_string ATTRIBUTE_HAS_A_VALUE _FME_BLANK_STRING_'@Value(_not_rendered_text_string)'FME_NUM_CONDITIONS2___
    -> BodyHTMLReportGenerator
Note: Assemble the final report from its sections.
ReportHTMLLayouter: HTMLLayouter
    DIV_STYLE = NONE
    LAYOUT = VERTICAL
    TITLE = Geometry Validation Report for Workspace: $(WORKSPACE_NAME)
    -> Report (output)
Report (output)

Bookmark: Generate the report sections.
Note: Generate the report header.
HeaderHTMLReportGenerator: HTMLReportGenerator
    CONTENT_LIST = HEADER HTML
    GROUP_BY = _mgs_calling_module _feature_id
    PAGE_CONFIG:
      HEADER{{TEXT;@Value(_mgs_calling_module);HEADER;H4;HEADER_ID;;ALIGNMENT;LEFT;COLOR;0,0,0;FME_CONTROLLER_QUERY_FILE;transformers/dependencies/html5/Header.fme;FME_CONTROLLER_CHOICE;Header}}HTML{{HTML;<div>
          <ul>
              <li>FME Build Number: $(FME_BUILD_NUM)</li>
              <li>FME Build Date: $(FME_BUILD_DATE)
              <li>FME Home: $(FME_HOME_UNIX_USERTYPED)</li>
              <li>FME Product Name: $(FME_PRODUCT_NAME)</li>
              <li>Test Ran At: @DateTimeFormat(@DateTimeNow(), %Y-%m-%d %H:%M:%S)</li>
          </ul>
      </div>;FME_CONTROLLER_QUERY_FILE;transformers/dependencies/html5/Custom HTML.fme;FME_CONTROLLER_CHOICE;Custom HTML}}
    TITLE = Geometry Validation Report Header
    -> HeaderAttributeCreator
Note: Generate the report body.
BodyHTMLReportGenerator: HTMLReportGenerator
    CONTENT_LIST = TABLE
    GROUP_BY = _mgs_calling_module
    PAGE_CONFIG = TABLE{{STYLE;HOVER;TABLE;_feature_label|Feature ID/_geometry_image_tag|Geometry/_issue_issue_found|Issue/_issue_location.x|X/_issue_location.y|Y/_issue_location.z|Z/_issue_repair_state|Repair State/_issue_supplementary_info|Supplementary Info/_issue_supplement_details|Supplement/_issue_supplement_location.x|SX/_issue_supplement_location.y|SY/_issue_supplement_location.z|SZ/_issue_supplement_original_part_index|Original Part Index;FME_CONTROLLER_QUERY_FILE;transformers/dependencies/html5/Table.fme;FME_CONTROLLER_CHOICE;Table}}
    TITLE = Geometry Validation Report Body
    -> BodyAttributeCreator

Bookmark: Set the report section order.
Note: The report header must come first.
HeaderAttributeCreator: AttributeCreator
    ATTR_TABLE = SET_TO _report_section_order = 0
    -> ReportSectionSorter
Note: The report body must come second.
BodyAttributeCreator: AttributeCreator
    ATTR_TABLE = SET_TO _report_section_order = 1
    -> ReportSectionSorter
Note: Sort the report sections and features.
ReportSectionSorter: Sorter
    SORT_PARM = _mgs_calling_module ALPHA ASCENDING _report_section_order NUMERIC ASCENDING
    SORTED -> ReportHTMLLayouter

Bookmark: Extract feature issues for reporting.
AttributeExposer
    ATTR_LIST = _issues{}.count,_issues{}.issue_found,_issues{}.location.x,_issues{}.location.y,_issues{}.location.z,_issues{}.location_sample.x,_issues{}.location_sample.y,_issues{}.location_sample.z,_issues{}.repair_state,_issues{}.supplementary_info
    -> IssuesListExploder
IssuesListExploder: ListExploder
    ATTR_ACCUM_MODE = Prefix List Attributes
    INCOMING_PREFIX = _issue_
    INDEX_ATTR = _original_issue_index
    LIST_ATTR = _issues{}
    ELEMENTS -> FeatureIssueCounter
FeatureIssueCounter: Counter
    CNT_ATTR = _feature_issue_index
    GROUP_BY = _feature_id
    SCOPE = Local
    START = 0
    -> IssueSampleLocationTester
IssueSampleLocationTester: Tester
    BOOL_OP = COMPOSITE
    COMPOSITE_TEST = 1 AND 2 AND 3
    TEST_CLAUSE:
      TEST _issue_location_sample.x ATTRIBUTE_HAS_A_VALUE ""
      TEST _issue_location_sample.y ATTRIBUTE_HAS_A_VALUE ""
      TEST _issue_location_sample.z ATTRIBUTE_HAS_A_VALUE ""
    TEST_MODE = TEST
    PASSED -> SupplementListAttributeExposer
    FAILED -> IssueSampleLocationAttributeCreator
IssueSampleLocationAttributeCreator: AttributeCreator
    ATTR_TABLE:
      SET_TO _issue_location.x = FME_CONDITIONAL:DEFAULT_VALUE'_FME_NO_OP_'BOOL_OP;OR;COMPOSITE_TEST;1;TEST _issue_location_sample.x ATTRIBUTE_HAS_A_VALUE _FME_BLANK_STRING_'@Value(_issue_location_sample.x) (sample)'FME_NUM_CONDITIONS2___
      SET_TO _issue_location.y = FME_CONDITIONAL:DEFAULT_VALUE'_FME_NO_OP_'BOOL_OP;OR;COMPOSITE_TEST;1;TEST _issue_location_sample.y ATTRIBUTE_HAS_A_VALUE _FME_BLANK_STRING_'@Value(_issue_location_sample.y) (sample)'FME_NUM_CONDITIONS2___
      SET_TO _issue_location.z = FME_CONDITIONAL:DEFAULT_VALUE'_FME_NO_OP_'BOOL_OP;OR;COMPOSITE_TEST;1;TEST _issue_location_sample.z ATTRIBUTE_HAS_A_VALUE _FME_BLANK_STRING_'@Value(_issue_location_sample.z) (sample)'FME_NUM_CONDITIONS2___
    -> SupplementListAttributeExposer

Bookmark: Extract issue supplements for reporting.
SupplementListAttributeExposer: AttributeExposer
    ATTR_LIST = _issue_supplementary_info{}.count,_issue_supplementary_info{}.details,_issue_supplementary_info{}.location.x,_issue_supplementary_info{}.location.y,_issue_supplementary_info{}.location.z,_issue_supplementary_info{}.location_sample.x,_issue_supplementary_info{}.location_sample.y,_issue_supplementary_info{}.location_sample.z,_issue_supplementary_info{}.original_part_index
    -> SupplementListExploder
SupplementListExploder: ListExploder
    ATTR_ACCUM_MODE = Prefix List Attributes
    INCOMING_PREFIX = _issue_supplement_
    LIST_ATTR = _issue_supplementary_info{}
    ELEMENTS -> FeatureIssueSupplementCounter
FeatureIssueSupplementCounter: Counter
    CNT_ATTR = _feature_issue_supplement_index
    GROUP_BY = _feature_id _feature_issue_index
    SCOPE = Local
    START = 0
    -> SupplementSampleLocationTester
SupplementSampleLocationTester: Tester
    BOOL_OP = COMPOSITE
    COMPOSITE_TEST = 1 AND 2 AND 3
    TEST_CLAUSE:
      TEST _issue_supplement_location_sample.x ATTRIBUTE_HAS_A_VALUE ""
      TEST _issue_supplement_location_sample.y ATTRIBUTE_HAS_A_VALUE ""
      TEST _issue_supplement_location_sample.z ATTRIBUTE_HAS_A_VALUE ""
    TEST_MODE = TEST
    PASSED -> IssueElementSorter
    FAILED -> SupplementSampleLocationAttributeCreator
SupplementSampleLocationAttributeCreator: AttributeCreator
    ATTR_TABLE:
      SET_TO _issue_supplement_location.x = FME_CONDITIONAL:DEFAULT_VALUE'_FME_NO_OP_'BOOL_OP;OR;COMPOSITE_TEST;1;TEST _issue_supplement_location_sample.x ATTRIBUTE_HAS_A_VALUE _FME_BLANK_STRING_'@Value(_issue_supplement_location_sample.x) (sample)'FME_NUM_CONDITIONS2___
      SET_TO _issue_supplement_location.y = FME_CONDITIONAL:DEFAULT_VALUE'_FME_NO_OP_'BOOL_OP;OR;COMPOSITE_TEST;1;TEST _issue_supplement_location_sample.y ATTRIBUTE_HAS_A_VALUE _FME_BLANK_STRING_'@Value(_issue_supplement_location_sample.y) (sample)'FME_NUM_CONDITIONS2___
      SET_TO _issue_supplement_location.z = FME_CONDITIONAL:DEFAULT_VALUE'_FME_NO_OP_'BOOL_OP;OR;COMPOSITE_TEST;1;TEST _issue_supplement_location_sample.z ATTRIBUTE_HAS_A_VALUE _FME_BLANK_STRING_'@Value(_issue_supplement_location_sample.z) (sample)'FME_NUM_CONDITIONS2___
    -> IssueElementSorter

Bookmark: Prepare each issue for display in its own report row.
IssueElementSorter
    _FEATURE_ID = @Value(_feature_id)
    _FEATURE_ISSUE_INDEX = @Value(_feature_issue_index)
    _FEATURE_ISSUE_SUPPLEMENT_INDEX = @Value(_feature_issue_supplement_index)
    _MGS_CALLING_MODULE = @Value(_mgs_calling_module)
    Sorted -> IssueSampler
Note: Separate initial feature issue supplement elements.
IssueSampler: Sampler
    GROUP_BY = _feature_id _mgs_calling_module _feature_issue_index _feature_issue_supplement_index
    RATE = 1
    SAMPLE_MODE = No
    SAMPLE_TYPE_LONG = First N Features
    SAMPLED -> IssueElementSorter_2
    NOT_SAMPLED -> AttributeManager
IssueElementSorter_2
    _FEATURE_ID = @Value(_feature_id)
    _FEATURE_ISSUE_INDEX = @Value(_feature_issue_index)
    _FEATURE_ISSUE_SUPPLEMENT_INDEX = @Value(_feature_issue_supplement_index)
    _MGS_CALLING_MODULE = @Value(_mgs_calling_module)
    Sorted -> EmptyFeatureLabelAttributeCreator
Note: Don't repeat the feature ID label for each issue.
EmptyFeatureLabelAttributeCreator: AttributeCreator
    ATTR_TABLE = SET_TO _feature_label
    -> IssueElementSorter_3

Bookmark: Don't repeat the issue field values for each supplement.
AttributeManager
    ATTR_TABLE:
      SET_TO _issue_count
      SET_TO _issue_issue_found
      SET_TO _issue_location.x
      SET_TO _issue_location.y
      SET_TO _issue_location.z
      SET_TO _issue_location_sample.x
      SET_TO _issue_location_sample.y
      SET_TO _issue_location_sample.z
      SET_TO _issue_repair_state
      SET_TO _issue_supplementary_info
      SET_TO _issue_supplement_count
      SET_TO _issue_supplement_details
      SET_TO _issue_supplement_location.x
      SET_TO _issue_supplement_location.y
      SET_TO _issue_supplement_location.z
      SET_TO _issue_supplement_location_sample.x
      SET_TO _issue_supplement_location_sample.y
      SET_TO _issue_supplement_location_sample.z
      SET_TO _issue_supplement_original_part_index
    -> GeometryRemover
GeometryRemover
    -> IssueElementSorter_2

FME custom transformer FileDeleter_3
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_2
Delete specified file - not using Python, but rather the FeatureWriter - Copy File approach to remove the file. 
Image by OpenClipart-Vectors from Pixabay

Parameters:
- FileToDelete =   # File to delete (full path including filename)

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer IssueElementSorter

Parameters:
- _FEATURE_ID = @Value(_feature_id)   # Feature Id
- _FEATURE_ISSUE_INDEX = @Value(_feature_issue_index)   # Feature Issue Index
- _FEATURE_ISSUE_SUPPLEMENT_INDEX = @Value(_feature_issue_supplement_index)   # Feature Issue Supplement Index
- _MGS_CALLING_MODULE = @Value(_mgs_calling_module)   # Mgs Calling Module

Input (input)
    -> Sorter
Sorter
    SORT_PARM = _mgs_calling_module ALPHA ASCENDING _feature_id NATURAL ASCENDING _feature_issue_index NUMERIC ASCENDING _feature_issue_supplement_index NUMERIC ASCENDING
    SORTED -> Sorted (output)
Sorted (output)

FME custom transformer Base64PNGRasterizer
Rasterize all rasterizable vector geometries arriving on the Input port, grouping them into output raster features by the provided id, _xmax, _xmin, _ymax, and _ymin attributes, plus the attributes named in the Custom_Attributes_to_Preserve user parameter. For each Output raster, include an _image_base64 attribute containing the base64 encoding of a PNG-formatted version of the raster. This attribute's contents are suitable for use with an HTML ￼￼img tag with inline src.
The vector geometry types currently supported for rasterization are:
Point
Line
Arc
Area
Ellipse
Text
Point Cloud
The following geometry types are not currently rendered (this is likely to change to some kind of planar projection or disaggregation as appropriate in a future enhancement):
Surface
Solid
Collection
Instance
Null
Rasters are passed through ungrouped, and unchanged with the sole exception that they are scaled to the requested dimensions.
IMPORTANT: This transformer must be embedded, not linked, for the calling module (workspace or linked custom transformer) to be properly identified; this is the default when you add it to your workflow.
This transformer is part of a suite that can be used for both data and workflow quality. For the former, data can be tested and exception reports generated from inside any workspace or transformer. For the latter, regression test driver workspaces can call a target workspace or transformer with predefined test data and verify that the results are correct and can be generated without error for both common and edge cases. For issues or questions, please Create an issue here. For the source, including test driver components, please see the Github repository.
Copyright © 2019-2022 by Modern geoSystems, released under this BSD 3-clause license.
Ports
Input
Feed all features that contain geometries to be rasterized.
Output
An ouput feature per group, with all the grouping attributes intact.  Each output feature includes the following additional attribute:
_image_base64 - the base64 encoding of a PNG-formatted version of the raster
Parameters
Specify the parameters for rasterization of the incoming features.
ID
The name of the attribute containing the identifier for each Input feature for grouping purposes.
Name
A name for this Base64PNGRasterizer instance to support the creation of unique temporary filenames.
Default_Pen_Color
The default line drawing color to use for rasterized vector geometries when none is specified.
Default_Fill_Color
The default fill color to use for rasterized vector geometries when none is specified.
_XMAX
The name of the attribute containing the maximum x value for the raster ground extents.
_XMIN
The name of the attribute containing the minimum x value for the raster ground extents.
_YMAX
The name of the attribute containing the maximum y value for the raster ground extents.
_YMIN
The name of the attribute containing the minimum y value for the raster ground extents.
Custom_Attributes_to_Preserve
A space-separated list of custom attributes to include in the grouping of Input features into Output raster features.  These attributes will be included with all Output features.

Parameters:
- ID = @Value(id)   # id
- Name =
- Default_Pen_Color = 0,0,0,1   # Default Pen Color
- Default_Fill_Color = 1,1,1,0   # Default Fill Color
- _XMAX = @Value(_xmax)   # Xmax
- _XMIN = @Value(_xmin)   # Xmin
- _YMAX = @Value(_ymax)   # Ymax
- _YMIN = @Value(_ymin)   # Ymin
- Custom_Attributes_to_Preserve =   # NO_EXPAND_LIST Custom Attributes to Preserve
- All_Attributes_to_Preserve:   # All Attributes to Preserve
      import fme
      import re
      
      
      # Initialize the grouping attribute list with all the existing attribute parameters and all internally-generated attributes.
      result = 'id _xmax _xmax_extent _xmin _xmin_extent _ymax _ymax_extent _ymin _ymin_extent _base64_geometry _number_of_columns _number_of_rows _saved_color _saved_fill_color _size_ratio _x _y fme_color fme_feature_type fme_fill_color fme_rotation fme_text_size fme_text_string _not_rendered_text_string'
      
      # Add any custom attributes specified in the transformer parameters.
      sample_user_parameter = next(name for name in FME_MacroValues.keys() if re.search(r'_(ID|_[XY]MAX|_[XY]MIN)', name) and not name.startswith('FME_'))
      parameter_prefix = '_'.join([component for component in sample_user_parameter.split('_') if len(component) > 0][0:-1])
      if len(fme.macroValues[parameter_prefix + '_Custom_Attributes_to_Preserve']) > 0:
          result += ' ' + fme.macroValues[parameter_prefix + '_Custom_Attributes_to_Preserve']
      
      return result

Input (input)
    -> GeometryExtractor
Note: Save the incoming feature's geometry.
GeometryExtractor
    ATTR = _base64_geometry
    KIND_LONG = FME Binary
    REMOVE_GEOMETRY = No
    -> ImageSizeAttributeCreator
Note: Output the geometry with a standard display width.
ImageSizeAttributeCreator: AttributeCreator
    ATTR_TABLE:
      SET_TO _number_of_columns = 256
      SET_TO _xmin_extent = @Evaluate(@Value(_xmin)-1)
      SET_TO _xmax_extent = @Evaluate(@Value(_xmax)+1)
      SET_TO _ymin_extent = @Evaluate(@Value(_ymin)-1)
      SET_TO _ymax_extent = @Evaluate(@Value(_ymax)+1)
      SET_TO _size_ratio = @Evaluate(@Value(_number_of_columns)/(@Value(_xmax_extent)-@Value(_xmin_extent)))
      SET_TO _number_of_rows = @Evaluate(@round((@Value(_ymax_extent)-@Value(_ymin_extent))*@Value(_size_ratio),0))
      SET_TO _not_rendered_text_string = FME_NULL_VALUE
    -> ValidExtentsTester
ValidExtentsTester: Tester
    BOOL_OP = COMPOSITE
    COMPOSITE_TEST = 1 AND 2 AND 3 AND 4
    TEST_CLAUSE:
      TEST _xmax_extent ATTRIBUTE_HAS_A_VALUE ""
      TEST _xmin_extent ATTRIBUTE_HAS_A_VALUE ""
      TEST _ymax_extent ATTRIBUTE_HAS_A_VALUE ""
      TEST _ymin_extent ATTRIBUTE_HAS_A_VALUE ""
    TEST_MODE = TEST
    PASSED -> ColorsAttributeExposer
    FAILED -> BadExtentsAttributeManager
ColorsAttributeExposer: AttributeExposer
    ATTR_LIST = fme_color,fme_fill_color
    -> Base64PNGRasterizerGeometryFilter [GeometryFilter_Input]
Base64PNGRasterizerGeometryFilter
    ToBeRasterized -> PenColorTester
    ToBeBlank -> SavedColorsAttributeCreator
    ToBeScaledOnly -> RasterScaler
RasterScaler: Scaler
    RASTER_SCALING = Extents
    SCALE_ORIGIN = Center Point
    TEXT_LOC_ONLY = Location and Size
    XSCALE = @Value(_size_ratio)
    YSCALE = @Value(_size_ratio)
    ZSCALE = @Value(_size_ratio)
    SCALED -> Base64PNGRasterizerGeometryFilter_2 [GeometryFilter_Input]
BadExtentsAttributeManager: AttributeManager
    ATTR_TABLE:
      SET_TO _number_of_columns = 1
      SET_TO _xmin_extent = 0
      SET_TO _xmax_extent = 1
      SET_TO _ymin_extent = 0
      SET_TO _ymax_extent = 1
      SET_TO _size_ratio = 1
      SET_TO _number_of_rows = 1
      SET_TO _xmax = 1
      SET_TO _xmin = 0
      SET_TO _ymax = 1
      SET_TO _ymin = 0
    -> SavedColorsAttributeCreator
ImageRasterizer
    ALPHA = 1.0
    ANTI_ALIASING = No
    BACKGROUND_ALPHA = 0.0
    BACKGROUND_COLOR = 1,1,1
    COLUMNS = @Value(_number_of_columns)
    FILL_WITH_NODATA = No
    GROUND_EXTENTS_MAX_X = @Value(_xmax_extent)
    GROUND_EXTENTS_MAX_Y = @Value(_ymax_extent)
    GROUND_EXTENTS_MIN_X = @Value(_xmin_extent)
    GROUND_EXTENTS_MIN_Y = @Value(_ymin_extent)
    GROUP_BY = $(All_Attributes_to_Preserve)
    INTERPRETATION_TYPE = RGBA32
    ROWCOL_OR_CELLSIZE = RowsColumns
    ROWS = @Value(_number_of_rows)
    SPECIFY_GROUND_EXTENTS = Specify ground extents
    TOLERANCE = 0.5
    RASTER -> Base64PNGRasterizerGeometryFilter_2 [GeometryFilter_Input]
Base64PNGRasterizerGeometryFilter_2
    ToBeRasterized -> RasterExtractor
    ToBeBlank -> SavedColorsAttributeExposer
    ToBeScaledOnly -> RasterExtractor
SavedColorsAttributeExposer: AttributeExposer
    ATTR_LIST = _saved_color,_saved_fill_color
    -> FMEColorsAttributeCreator
Note: Restore the saved geometry colors over the blank image colors.
FMEColorsAttributeCreator: AttributeCreator
    ATTR_TABLE:
      SET_TO fme_color = @Value(_saved_color)
      SET_TO fme_fill_color = @Value(_saved_fill_color)
    -> RasterExtractor
Note: Extract a PNG-formatted image binary attribute.
RasterExtractor
    RASTER_BLOB_ATTR = _image
    RASTER_FORMAT = PNGRASTER
    RASTER_FORMAT_ATTR = _rasterFormatName
    -> ImageBinaryEncoder
Note: Base-64 Encode the PNG binary.
ImageBinaryEncoder: BinaryEncoder
    ATTR_TABLE = _image _image_base64
    ENCODING_TYPE = Base64
    -> Output (output)
Output (output)

Bookmark: Set default colors if not already specified.
PenColorTester: Tester
    BOOL_OP = OR
    TEST_CLAUSE = TEST fme_color ATTRIBUTE_HAS_A_VALUE ""
    TEST_MODE = TEST
    PASSED -> FillColorTester
    FAILED -> PenColorAttributeCreator
PenColorAttributeCreator: AttributeCreator
    ATTR_TABLE = SET_TO fme_color = $(Default_Pen_Color)
    -> FillColorTester
FillColorTester: Tester
    BOOL_OP = OR
    TEST_CLAUSE = TEST fme_fill_color ATTRIBUTE_HAS_A_VALUE ""
    TEST_MODE = TEST
    PASSED -> ImageRasterizer
    FAILED -> FillColorAttributeCreator
FillColorAttributeCreator: AttributeCreator
    ATTR_TABLE = SET_TO fme_fill_color = $(Default_Fill_Color)
    -> ImageRasterizer

Bookmark: Set a dummy vertex for a blank image.
SavedColorsAttributeCreator: AttributeCreator
    ATTR_TABLE:
      SET_TO _saved_color = @Value(fme_color)
      SET_TO _saved_fill_color = @Value(fme_fill_color)
    -> BlankImageAttributeCreator
BlankImageAttributeCreator: AttributeCreator
    ATTR_TABLE:
      SET_TO _x = @Evaluate(@round((@Value(_xmax_extent)-@Value(_xmin_extent))/2,0))
      SET_TO _y = @Evaluate(@round((@Value(_ymax_extent)-@Value(_ymin_extent))/2,0))
      SET_TO _not_rendered_text_string = Not Rendered
    -> DummyVertexCreator
DummyVertexCreator: VertexCreator
    MEASURE_TYPE = Continuous
    MODE_NAME = Replace with Point
    XVAL = @Value(_x)
    YVAL = @Value(_y)
    -> BlankFeatureColorSetter
BlankFeatureColorSetter: FeatureColorSetter
    COLOR = $(Default_Fill_Color)
    FILL_COLOR = $(Default_Fill_Color)
    MODE = Fixed
    COLORED -> ImageRasterizer

FME custom transformer GeometryValidationCallerPopulator

Parameters:
- _FEATURE_ID = @Value(_feature_id)   # Feature Id

Input (input)
    -> AttributeCreator
Note: Assemble the calling module name attribute for reporting purposes.
AttributeCreator
    ATTR_TABLE = SET_TO _mgs_calling_module = $(FME_MF_DIR_USERTYPED)$(FME_MF_NAME)
    -> OriginalFeatureTester
OriginalFeatureTester: Tester
    BOOL_OP = OR
    TEST_CLAUSE = TEST _issues{0}.issue_found NOT_ATTRIBUTE_HAS_A_VALUE ""
    TEST_MODE = TEST
    PASSED -> Original (output)
    FAILED -> PythonCaller
Original (output)
Note: Update the repair stati to be more human-intelligible in a reporting context.
PythonCaller
    PYTHONSOURCE:
      import fme
      import fmeobjects


      class FeatureProcessor(object):
          """Template Class Interface:
          When using this class, make sure its name is set as the value of the 'Class
          to Process Features' transformer parameter.
          """

          def __init__(self):
              """Base constructor for class members."""
              pass

          def input(self, feature):
              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              issues = feature.getAttribute('_issues{}.issue_found')
              if issues:
                  for i, issue in enumerate(issues):
                      repair_is_null, repair_is_missing, repair_type = feature.getAttributeNullMissingAndType('_issues{' + str(i) + '}.repair_state')
                      repair = (('Repaired' if len(issues) == 1 else '') if (repair_is_null or repair_is_missing) else feature.getAttribute('_issues{' + str(i) + '}.repair_state'))
                      feature.setAttribute('_issues{' + str(i) + '}.repair_state', repair)
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> Exceptions (output)
Exceptions (output)
