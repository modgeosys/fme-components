FME workspace TestAttributeValidation.fmw

Parameters:
- FME_SHAREDRESOURCE_DATA = Resources/Data
- FME_SHAREDRESOURCE_TEMP = Resources/Temp

Creator
    GEOMTYPE = Geometry Object
    NUM = 2
    CREATED -> Counter
Counter
    CNT_ATTR = id
    DOMAIN = record_id_counter
    SCOPE = Global
    START = 0
    -> AttributeCreator
AttributeCreator
    ATTR_TABLE:
      SET_TO string1 = dummy
      SET_TO int1 = 1
      SET_TO string2 = whatever
    -> StatisticsCalculator
StatisticsCalculator
    COMPUTE_HISTOGRAM = NO
    COUNT_ATTR = _input_feature_count
    PREPEND_ATTR_NAME_CHOICE = For multiple results only
    STATS_ATTRS = id
    COMPLETE -> InputFeatureCountAttributeValidator
InputFeatureCountAttributeValidator: AttributeValidator
    TABLE = _input_feature_count;RANGE;(1,3]
    PASSED -> FirstAttributeValidator
    FAILED -> DuplicateFilter
FirstAttributeValidator: AttributeValidator
    TABLE = string1;ATTRIBUTE_HAS_A_VALUE;<Unused>/int1;RANGE;(-1,1)
    FAILED -> FirstAttributeValidationListPopulator
FirstAttributeValidationListPopulator: AttributeValidationListPopulator
    Validator_Name = First
    -> SecondAttributeValidator
SecondAttributeValidator: AttributeValidator
    TABLE = string2;CONTAINS_REGEX;special
    FAILED -> SecondAttributeValidationListPopulator
SecondAttributeValidationListPopulator: AttributeValidationListPopulator
    Validator_Name = Second
    -> AttributeValidationHTMLReportGenerator
DuplicateFilter
    INPUT_ORDERED_CHOICE = No
    KEYATTR = _input_feature_count
    UNIQUE -> AttributeRemover
AttributeRemover
    REMOVE_ATTRS = id
    -> InputFeatureCountAttributeValidationListPopulator
InputFeatureCountAttributeValidationListPopulator: AttributeValidationListPopulator
    Validator_Name = InputFeatureCount
    -> AttributeValidationHTMLReportGenerator
Creator_2
    GEOMTYPE = Geometry Object
    NUM = 1
    CREATED -> AttributeValidationTestTransformer
AttributeValidationTestTransformer
    _CREATION_INSTANCE = @Value(_creation_instance)
    -> AttributeValidationHTMLReportGenerator
AttributeValidationHTMLReportGenerator
    _FEATURE_ID = @Value(id)
    -> ReportFeatureWriter [HTML]
ReportFeatureWriter: FeatureWriter
    DATASET = $(FME_SHAREDRESOURCE_DATA)/Output/TestResults.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
    HTML -> TestStatusAttributeFilter
TestStatusAttributeFilter: AttributeFilter
    ATTR_NAME = _test_status
    ATTR_VALUES = <Empty>,<Missing>,<Null>,<Unfiltered>,SUCCEEDED,FAILED
    FAILED -> Terminator
Terminator
    MESSAGE = Test Failure

FME custom transformer TestTransformer

Parameters:
- _CREATION_INSTANCE =

ModuleAttributeValidator_Input (input)
    -> ModuleAttributeValidator
ModuleAttributeValidator: AttributeValidator
    TABLE = _creation_instance;TYPE;XML
    FAILED -> AttributeValidationListPopulator_Output_1 (output)
AttributeValidationListPopulator_Output_1 (output)

FME custom transformer AttributeValidationListPopulator
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)
