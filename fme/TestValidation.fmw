FME workspace TestValidation.fmw

Parameters:
- DestDataset_HTML = $(FME_MF_DIR)Resources/Data/Output/TestResults.html   # HTML Files(*.html)|*.html Destination Html File

Writers:
- HTML_1: HTML to $(DestDataset_HTML)

Creator
    GEOMTYPE = Geometry Object
    NUM = 2
    CREATED -> Counter
Counter
    CNT_ATTR = id
    DOMAIN = record_id_counter
    SCOPE = Global
    START = 0
    -> AttributeCreator
AttributeCreator
    ATTR_TABLE:
      SET_TO string1 = dummy
      SET_TO int1 = 1
      SET_TO string2 = whatever
    -> StatisticsCalculator
StatisticsCalculator
    COMPUTE_HISTOGRAM = NO
    COUNT_ATTR = _input_feature_count
    PREPEND_ATTR_NAME_CHOICE = For multiple results only
    STATS_ATTRS = id
    COMPLETE -> InputRecordCountAttributeValidator
InputRecordCountAttributeValidator: AttributeValidator
    TABLE = _input_feature_count;RANGE;(1,3]
    PASSED -> FirstAttributeValidator
    FAILED -> DuplicateFilter
FirstAttributeValidator: AttributeValidator
    TABLE = string1;ATTRIBUTE_HAS_A_VALUE;<Unused>/int1;RANGE;(-1,1)
    FAILED -> FirstValidatorListPopulator
FirstValidatorListPopulator: ValidatorListPopulator
    Validator_Name = First
    -> SecondAttributeValidator
SecondAttributeValidator: AttributeValidator
    TABLE = string2;CONTAINS_REGEX;special
    FAILED -> SecondValidatorListPopulator
SecondValidatorListPopulator: ValidatorListPopulator
    Validator_Name = Second
    -> ValidationHTMLReportGenerator
DuplicateFilter
    INPUT_ORDERED_CHOICE = No
    KEYATTR = _input_feature_count
    UNIQUE -> AttributeRemover
AttributeRemover
    REMOVE_ATTRS = id
    -> InputFeatureCountValidatorListPopulator
InputFeatureCountValidatorListPopulator: ValidatorListPopulator
    Validator_Name = InputFeatureCount
    -> ValidationHTMLReportGenerator
Creator_2
    GEOMTYPE = Geometry Object
    NUM = 1
    CREATED -> ValidationTestTransformer [ModuleAttributeValidator_Input]
ValidationTestTransformer
    _CREATION_INSTANCE = @Value(_creation_instance)
    ValidatorListPopulator_Output_1 -> ValidationHTMLReportGenerator
ValidationHTMLReportGenerator
    _FEATURE_ID = @Value(id)
    -> HTML (writer HTML_1)
HTML (writer HTML_1)
    attributes: html_content buffer

FME custom transformer ValidatorListPopulator_2

Parameters:
- Validator_Name =   # Validator Name

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)/@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          index = 0
          for message in messages:
              if feature.getAttributeNullMissingAndType('_fme_validation_message_list{' + str(index) + '}.validator_name')[1]:
                  feature.setAttribute('_fme_validation_message_list{' + str(index) + '}.validator_name', feature.getAttribute('_mgs_validator_name'))
                  feature.setAttribute('_fme_validation_message_list{' + str(index) + '}.calling_module', feature.getAttribute('_mgs_calling_module'))
              index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer ValidatorListPopulator

Parameters:
- Validator_Name =   # Validator Name

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)/@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          index = 0
          for message in messages:
              if feature.getAttributeNullMissingAndType('_fme_validation_message_list{' + str(index) + '}.validator_name')[1]:
                  feature.setAttribute('_fme_validation_message_list{' + str(index) + '}.validator_name', feature.getAttribute('_mgs_validator_name'))
                  feature.setAttribute('_fme_validation_message_list{' + str(index) + '}.calling_module', feature.getAttribute('_mgs_calling_module'))
              index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer ValidationHTMLReportGenerator

Parameters:
- _RECORD_ID = @Value(_record_id)   # Record Id

PythonCaller_Input (input)
    -> PythonCaller
PythonCaller
    NEW_ATTRIBUTES = _mgs_validation_message _mgs_validation_name
    PYTHONSOURCE:
      import fme
      import fmeobjects

      class FeatureProcessor(object):
          def __init__(self):
              pass

          def input(self,feature):
              messages = feature.getAttribute('_fme_validation_message_list')
              attribute_names = feature.getAllAttributeNames()
              index = 0
              for message in messages:
                  exploded_feature = feature.clone()
                  exploded_feature.setAttribute('_mgs_validation_message', feature.getAttribute('_fme_validation_message_list{' + str(index) + '}'))
                  exploded_feature.setAttribute('_mgs_validation_name', feature.getAttribute('_fme_validation_message_list{' + str(index) + '}.validator_name'))
                  exploded_feature.removeAttribute('_fme_validation_message_list{}')
                  exploded_feature.removeAttribute('_fme_validation_message_list{}.validator_name')
                  self.pyoutput(exploded_feature)
                  index += 1

          def close(self):
              pass
    PYTHONSYMBOL = FeatureProcessor
    -> HTMLReportGenerator
HTMLReportGenerator
    CONTENT_LIST = HEADER TABLE
    PAGE_CONFIG = HEADER{{TEXT;Test Results for $(WORKSPACE_NAME) at $(FME_MF_NAME);HEADER;H1;ALIGNMENT;CENTER;COLOR;0,0,0;FME_CONTROLLER_QUERY_FILE;transformers/dependencies/html5/Header.fme}}TABLE{{STYLE;STRIPED;TABLE;_record_id|Record ID/_mgs_validation_name|Validator/_mgs_validation_message|Message;FME_CONTROLLER_QUERY_FILE;transformers/dependencies/html5/Table.fme}}
    -> HTMLReportGenerator_Output (output)
HTMLReportGenerator_Output (output)

FME custom transformer TestTransformer

Parameters:
- _CREATION_INSTANCE = @Value(_creation_instance)   # Creation Instance

ModuleAttributeValidator_Input (input)
    -> ModuleAttributeValidator
ModuleAttributeValidator: AttributeValidator
    TABLE = _creation_instance;TYPE;XML
    FAILED -> ValidatorListPopulator
ValidatorListPopulator
    Validator_Name = Module
    -> ValidatorListPopulator_Output_1 (output)
ValidatorListPopulator_Output_1 (output)
