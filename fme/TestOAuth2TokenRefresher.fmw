FME workspace TestOAuth2TokenRefresher.fmw
History: 2018-03-08,Kevin Weller,Updates to reflect move from GitHub to Assembla and Atlassian.

Parameters:
- Data_Directory = $(FME_SHAREDRESOURCE_DATA)   # Data Directory
- Configuration_File = QBO_APIConfiguration.json   # Configuration File
- DestDataset_FFS = $(Data_Directory)/Output/TestOAuth2TokenRefresher_output.ffs   # Destination FME Feature Store (FFS) File
- FME_SHAREDRESOURCE_DATA = $(FME_MF_DIR_USERTYPED)/Resources/Data   # FME Server Resource Data

Writers:
- FFS_1: FFS to $(DestDataset_FFS)

Creator
    GEOMTYPE = Geometry Object
    NUM = 1
    CREATED -> ConfigFileHTTPCaller
ConfigFileHTTPCaller: HTTPCaller
    RESPONSE_HEADER_LIST_ATTR = _headers
    STATUS_CODE_ATTR = _http_status_code
    FOLLOW_REDIRECTS = Yes
    FILE_PATH_ATTR = _response_file_path
    SAVE_MULTI = No
    HTTP_METHOD = GET
    TRANSFER_TIMEOUT_LENGTH = 90
    SAVE_FILE = File
    USE_COOKIES = No
    VERIFY_SSL_CERTIFICATES = Yes
    ERROR_ATTR = _error
    TARGET_URL = https://modgeosys.assembla.com/spaces/fme-components/subversion/source/HEAD/trunk/fme/Resources/Data/Auth/QBO_APIConfiguration_test.json?_format=raw
    CONNECTION_TIMEOUT_LENGTH = 60
    OUTPUT_FILENAME = $(FME_SHAREDRESOURCE_DATA)/Auth/QBO_APIConfiguration.json
    -> RefreshTokenFileHTTPCaller
RefreshTokenFileHTTPCaller: HTTPCaller
    RESPONSE_HEADER_LIST_ATTR = _headers
    STATUS_CODE_ATTR = _http_status_code
    FOLLOW_REDIRECTS = Yes
    FILE_PATH_ATTR = _response_file_path
    SAVE_MULTI = No
    HTTP_METHOD = GET
    TRANSFER_TIMEOUT_LENGTH = 90
    SAVE_FILE = File
    USE_COOKIES = No
    VERIFY_SSL_CERTIFICATES = Yes
    ERROR_ATTR = _error
    TARGET_URL = https://modgeosys.assembla.com/spaces/fme-components/subversion/source/HEAD/trunk/fme/Resources/Data/Auth/QBO_RefreshToken_test.txt?_format=raw
    CONNECTION_TIMEOUT_LENGTH = 60
    OUTPUT_FILENAME = $(FME_SHAREDRESOURCE_DATA)/Auth/QBO_RefreshToken.txt
    -> OAuth2ParametersAttributeCreator
OAuth2ParametersAttributeCreator: AttributeCreator
    ATTR_TABLE:
      SET_TO data_directory = $(Data_Directory)
      SET_TO api_configuration_filename = $(Configuration_File)
    -> OAuth2TokenRefresher
OAuth2TokenRefresher
    OAUTH2_CONFIGURATION_FILENAME = @Value(api_configuration_filename)
    OAUTH2_DATA_DIRECTORY = @Value(data_directory)
    <Rejected> -> SchemaSetter
    -> SchemaSetter
SchemaSetter
    SORT = None
    -> NewFeatureType (writer FFS_1)
NewFeatureType (writer FFS_1)

FME custom transformer SchemaSetter
This transformer adds both exposed and unexposed attributes to a feature-based schema, with appropriate data types. 
For example: if a feature has the following attributes:
    Attribute(boolean) : `mybool' has value `Yes'
    Attribute(32 bit integer): `myint' has value `12'
    Attribute(64 bit real) : `myreal' has value `12.965'
the following list attributes will be added:
    Attribute(string) : `attribute{0}.fme_data_type' has value `fme_boolean' 
    Attribute(encoded: utf-8): `attribute{0}.name' has value `mybool' 
    Attribute(string) : `attribute{1}.fme_data_type' has value `fme_int32' 
    Attribute(encoded: utf-8): `attribute{1}.name' has value `myint' 
    Attribute(string) : `attribute{2}.fme_data_type' has value `fme_real64' 
    Attribute(encoded: utf-8): `attribute{2}.name' has value `myreal' 
The transformer also gives users the option to exclude certain attributes based on name or prefix, and automatically excludes all "fme_" attributes.
Input Ports
Features containing attributes for which a schema definition is required. 
    Output Ports
All features are output. Attributes which have been selected to be excluded are removed from the feature. The list containing the schema of the feature is added to each feature. 
    Parameters
    Attributes to Exclude
A selected set of attributes that will be excluded from the generated schema list and removed from the feature.
    Prefixes to Exclude
A comma-delimited list of prefixes for attributes that are to be excluded from the generated schema list and removed from the feature. Regular expressions are not supported. For example: "date" will exclude any attributes that start with the letters "date" e.g. date_created, dateupdated
    Sort Attributes
(Ascending, Descending, None) Set this parameter to alphabetically sort output attributes.
    Usage Notes
The feature based schema can be passed to any writer that it set to Dynamic Mode and used with the "Schema from First Feature" setting.
Please see 
        https://knowledge.safe.com/articles/1051/dynamic-workflow-tutorial-destination-schema-is-de-2.html 
    for more information on feature-based schema using list attributes.

Parameters:
- AttributesToExclude =   # " " Attributes to exclude
- PrefixesToExclude =   # Prefixes to exclude
- SORT = None   # Sort Attributes

Input (input)
    -> ParameterFetcher
Note: Retrieve Parameters
ParameterFetcher
    ATTR_LIST = _AttributesToExclude {$(AttributesToExclude)} _PrefixesToExclude {$(PrefixesToExclude)} _sort {$(SORT)}
    -> PythonCaller
Note: See Comment in Code
PythonCaller
    PYTHONSYMBOL = FeatureProcessor
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':
                     type=feature.getAttributeType(att)
                     #Check datatype and set in schema
                     type = self.typesMapping[type]

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Output (output)
