FME workspace TestDatasetValidatorWithGeometries.fmw

Parameters:
- FME_SHAREDRESOURCE_DATA = Resources/Data
- FME_SHAREDRESOURCE_TEMP = Resources/Temp

Note: Alternate expected test data with null geometries.
Creator_5
    GEOMTYPE = Geometry Object
    NUM = 3
Note: Box centered on origin.
Creator_1
    COORDS = -10 -10 -10 10 10 10 10 -10 -10 -10
    GEOMTYPE = 2D Coordinate List
    NUM = 3
    CREATED -> Counter
Counter
    CNT_ATTR = id
    DOMAIN = id_counter
    SCOPE = Global
    START = 0
    -> Logger
    -> DatasetValidator [Expected]
Note: Box shifted.
Creator_2
    COORDS = -5 -5 -5 15 15 15 15 -5 -5 -5
    GEOMTYPE = 2D Coordinate List
    NUM = 1
    CREATED -> AttributeCreator_2
AttributeCreator_2
    ATTR_TABLE = SET_TO id = 0
    -> Logger
    -> DatasetValidator [Actual]
Note: Identical box to expected.
Creator_3
    COORDS = -10 -10 -10 10 10 10 10 -10 -10 -10
    GEOMTYPE = 2D Coordinate List
    NUM = 1
    CREATED -> AttributeCreator_3
AttributeCreator_3
    ATTR_TABLE = SET_TO id = 1
    -> Logger
    -> DatasetValidator [Actual]
Note: Null geometry.
Creator_4
    GEOMTYPE = Geometry Object
    NUM = 1
    CREATED -> AttributeCreator_4
AttributeCreator_4
    ATTR_TABLE = SET_TO id = 2
    -> Logger
    -> DatasetValidator [Actual]
DatasetValidator
    ID = @Value(id)
    Ignore_Unmatched_Features = No
    Transient_Attribute_Names = ^(postgres|postgis|job|csv|salesforce|Loop)?[_ ]
    Validator_Name = Geometries
    Report -> ReportFeatureWriter [HTML]
ReportFeatureWriter: FeatureWriter
    DATASET = $(FME_SHAREDRESOURCE_DATA)/Output/TestDatasetValidatorWithGeometries.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
    HTML -> TestStatusAttributeFilter
TestStatusAttributeFilter: AttributeFilter
    ATTR_NAME = _test_status
    ATTR_VALUES = <Empty>,<Missing>,<Null>,<Unfiltered>,SUCCEEDED,FAILED
    FAILED -> Terminator
Terminator
    MESSAGE = Test Failure
Logger
    LOG_FEATURE = LOG_ONLY
    MAXCOORDS = 20
    MAXFEATS = 20
    MESSAGE = Feature is:
    SEVERITY = INFO

FME custom transformer Base64PNGRasterizerGeometryFilter_13

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_4
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_11
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_20
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_14

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_19
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_8

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_9
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_5
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_26
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_26

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_7
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_25
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_5

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_3

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_15
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizer
Rasterize all rasterizable vector geometries arriving on the Input port, grouping them into output raster features by the provided id, _xmax, _xmin, _ymax, and _ymin attributes, plus the attributes named in the Custom_Attributes_to_Preserve user parameter. For each Output raster, include an _image_base64 attribute containing the base64 encoding of a PNG-formatted version of the raster. This attribute's contents are suitable for use with an inline HTML ￼￼ tag.
The vector geometry types currently supported for rasterization are:
Point
Line
Arc
Area
Ellipse
Text
Point Cloud
The following geometry types are not currently rendered (this is likely to change to some kind of planar projection or disaggregation as appropriate in a future enhancement):
Surface
Solid
Collection
Instance
Null
Rasters are passed through ungrouped, and unchanged with the sole exception that they are scaled to the requested dimensions.
IMPORTANT: This transformer must be embedded, not linked, for the calling module (workspace or linked custom transformer) to be properly identified; this is the default when you add it to your workflow.
This transformer is part of a suite that can be used for both data and workflow quality. For the former, data can be tested and exception reports generated from inside any workspace or transformer. For the latter, regression test driver workspaces can call a target workspace or transformer with predefined test data and verify that the results are correct and can be generated without error for both common and edge cases. For issues or questions, please Create an issue here. For the source, including test driver components, please see the Github repository.
Copyright © 2019-2022 by Modern geoSystems, released under this BSD 3-clause license.
Ports
Input
Feed all features that contain geometries to be rasterized.
Output
An ouput feature per group, with all the grouping attributes intact.  Each output feature includes the following additional attribute:
_image_base64 - the base64 encoding of a PNG-formatted version of the raster
Parameters
Specify the parameters for rasterization of the incoming features.
ID
The name of the attribute containing the identifier for each Input feature for grouping purposes.
Name
A name for this Base64PNGRasterizer instance to support the creation of unique temporary filenames.
Default_Pen_Color
The default line drawing color to use for rasterized vector geometries when none is specified.
Default_Fill_Color
The default fill color to use for rasterized vector geometries when none is specified.
_XMAX
The name of the attribute containing the maximum x value for the raster ground extents.
_XMIN
The name of the attribute containing the minimum x value for the raster ground extents.
_YMAX
The name of the attribute containing the maximum y value for the raster ground extents.
_YMIN
The name of the attribute containing the minimum y value for the raster ground extents.
Custom_Attributes_to_Preserve
A space-separated list of custom attributes to include in the grouping of Input features into Output raster features.  These attributes will be included with all Output features.

Parameters:
- All_Attributes_to_Preserve =
- Custom_Attributes_to_Preserve =
- Default_Fill_Color =
- Default_Pen_Color =
- ID =
- Name =
- PNG_Rootname =
- _XMAX =
- _XMIN =
- _YMAX =
- _YMIN =

Input (input)
    -> GeometryExtractor
Note: Save the incoming feature's geometry.
GeometryExtractor
    ATTR = _base64_geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> ImageSizeAttributeCreator
Note: Output the geometry with a standard display width.
ImageSizeAttributeCreator: AttributeCreator
    ATTR_TABLE:
      SET_TO _number_of_columns = 256
      SET_TO _xmin_extent = @Evaluate(@Value(_xmin)-1)
      SET_TO _xmax_extent = @Evaluate(@Value(_xmax)+1)
      SET_TO _ymin_extent = @Evaluate(@Value(_ymin)-1)
      SET_TO _ymax_extent = @Evaluate(@Value(_ymax)+1)
      SET_TO _size_ratio = @Evaluate(@Value(_number_of_columns)/(@Value(_xmax_extent)-@Value(_xmin_extent)))
      SET_TO _number_of_rows = @Evaluate(@round((@Value(_ymax_extent)-@Value(_ymin_extent))*@Value(_size_ratio),0))
      SET_TO _not_rendered_text_string = FME_NULL_VALUE
    -> ValidExtentsTester
ValidExtentsTester: Tester
    BOOL_OP = COMPOSITE
    COMPOSITE_TEST = 1 AND 2 AND 3 AND 4
    TEST_CLAUSE:
      TEST _xmax_extent ATTRIBUTE_HAS_A_VALUE ""
      TEST _xmin_extent ATTRIBUTE_HAS_A_VALUE ""
      TEST _ymax_extent ATTRIBUTE_HAS_A_VALUE ""
      TEST _ymin_extent ATTRIBUTE_HAS_A_VALUE ""
    TEST_MODE = TEST
    PASSED -> ColorsAttributeExposer
    FAILED -> BadExtentsAttributeManager
ColorsAttributeExposer: AttributeExposer
    ATTR_LIST = fme_color,fme_fill_color
    -> Base64PNGRasterizerGeometryFilter [GeometryFilter_Input]
Base64PNGRasterizerGeometryFilter
    ToBeRasterized -> PenColorTester
    ToBeBlank -> SavedColorsAttributeCreator
    ToBeScaledOnly -> RasterScaler
RasterScaler: Scaler
    RASTER_SCALING = Extents
    SCALE_ORIGIN = Center Point
    TEXT_LOC_ONLY = Location and Size
    XSCALE = @Value(_size_ratio)
    YSCALE = @Value(_size_ratio)
    ZSCALE = @Value(_size_ratio)
    SCALED -> ParameterFetcher
BadExtentsAttributeManager: AttributeManager
    ATTR_TABLE:
      SET_TO _number_of_columns = 1
      SET_TO _xmin_extent = 0
      SET_TO _xmax_extent = 1
      SET_TO _ymin_extent = 0
      SET_TO _ymax_extent = 1
      SET_TO _size_ratio = 1
      SET_TO _number_of_rows = 1
      SET_TO _xmax = 1
      SET_TO _xmin = 0
      SET_TO _ymax = 1
      SET_TO _ymin = 0
    -> SavedColorsAttributeCreator
ImageRasterizer
    ALPHA = 1.0
    ANTI_ALIASING = No
    BACKGROUND_ALPHA = 0.0
    BACKGROUND_COLOR = 1,1,1
    COLUMNS = @Value(_number_of_columns)
    FILL_WITH_NODATA = No
    GROUND_EXTENTS_MAX_X = @Value(_xmax_extent)
    GROUND_EXTENTS_MAX_Y = @Value(_ymax_extent)
    GROUND_EXTENTS_MIN_X = @Value(_xmin_extent)
    GROUND_EXTENTS_MIN_Y = @Value(_ymin_extent)
    GROUP_BY = $(All_Attributes_to_Preserve)
    INTERPRETATION_TYPE = RGBA32
    ROWCOL_OR_CELLSIZE = RowsColumns
    ROWS = @Value(_number_of_rows)
    SPECIFY_GROUND_EXTENTS = Specify ground extents
    TOLERANCE = 0.5
    RASTER -> ParameterFetcher
Note: Grab the temporary filename components.
ParameterFetcher
    ATTR_LIST = _PNG_Rootname $(PNG_Rootname) _Name $(Name)
    -> PNGFeatureWriter [Raster]
Note: Save the raster in PNG format.
PNGFeatureWriter: FeatureWriter
    DATASET = $(FME_MF_DIR_ENCODED)Resources/Temp/
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
    Raster -> GeometryReplacer
Note: Restore the incoming feature's geometry.
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_base64_geometry)
    SRS_AXIS_ORDER_DISPLAY = Automatic
    -> Base64PNGRasterizerGeometryFilter_2 [GeometryFilter_Input]
Base64PNGRasterizerGeometryFilter_2
    ToBeRasterized -> AttributeFileReader
    ToBeBlank -> SavedColorsAttributeExposer
    ToBeScaledOnly -> AttributeFileReader
SavedColorsAttributeExposer: AttributeExposer
    ATTR_LIST = _saved_color,_saved_fill_color
    -> FMEColorsAttributeCreator
Note: Restore the saved geometry colors over the blank image colors.
FMEColorsAttributeCreator: AttributeCreator
    ATTR_TABLE:
      SET_TO fme_color = @Value(_saved_color)
      SET_TO fme_fill_color = @Value(_saved_fill_color)
    -> AttributeFileReader
Note: Load the raw PNG binary.
AttributeFileReader
    CHAR_ENCODING = fme-binary
    DEST_ATTR = _image
    FILE_NAME = $(FME_MF_DIR_ENCODED)Resources/Temp/$(PNG_Rootname)_@Value(_Name)_@Value(id).png
    -> ImageBinaryEncoder
Note: Base-64 Encode the PNG binary.
ImageBinaryEncoder: BinaryEncoder
    ATTR_TABLE = _image _image_base64
    ENCODING_TYPE = Base64
    -> FileDeleter
Note: Delete the temporary PNG file.
FileDeleter
    FileToDelete = $(FME_MF_DIR)Resources/Temp/$(PNG_Rootname)_@Value(_Name)_@Value(id).png
    -> Output (output)
Output (output)

Bookmark: Set default colors if not already specified.
PenColorTester: Tester
    BOOL_OP = OR
    COMPOSITE_TEST = 1
    TEST_CLAUSE = TEST fme_color ATTRIBUTE_HAS_A_VALUE ""
    TEST_MODE = TEST
    PASSED -> FillColorTester
    FAILED -> PenColorAttributeCreator
PenColorAttributeCreator: AttributeCreator
    ATTR_TABLE = SET_TO fme_color = $(Default_Pen_Color)
    -> FillColorTester
FillColorTester: Tester
    BOOL_OP = OR
    COMPOSITE_TEST = 1
    TEST_CLAUSE = TEST fme_fill_color ATTRIBUTE_HAS_A_VALUE ""
    TEST_MODE = TEST
    PASSED -> ImageRasterizer
    FAILED -> FillColorAttributeCreator
FillColorAttributeCreator: AttributeCreator
    ATTR_TABLE = SET_TO fme_fill_color = $(Default_Fill_Color)
    -> ImageRasterizer

Bookmark: Set a dummy vertex for a blank image.
SavedColorsAttributeCreator: AttributeCreator
    ATTR_TABLE:
      SET_TO _saved_color = @Value(fme_color)
      SET_TO _saved_fill_color = @Value(fme_fill_color)
    -> BlankImageAttributeCreator
BlankImageAttributeCreator: AttributeCreator
    ATTR_TABLE:
      SET_TO _x = @Evaluate(@round((@Value(_xmax_extent)-@Value(_xmin_extent))/2,0))
      SET_TO _y = @Evaluate(@round((@Value(_ymax_extent)-@Value(_ymin_extent))/2,0))
      SET_TO _not_rendered_text_string = Not Rendered
    -> DummyVertexCreator
DummyVertexCreator: VertexCreator
    MEASURE_TYPE = Continuous
    MODE_NAME = Replace with Point
    XVAL = @Value(_x)
    YVAL = @Value(_y)
    -> BlankFeatureColorSetter
BlankFeatureColorSetter: FeatureColorSetter
    COLOR = $(Default_Fill_Color)
    FILL_COLOR = $(Default_Fill_Color)
    MODE = Fixed
    COLORED -> ImageRasterizer

FME custom transformer Base64PNGRasterizerGeometryFilter_2

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer AttributeValidationListPopulator_3
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer Base64PNGRasterizerGeometryFilter_16

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_10

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_20

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_17

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_4

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_6
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_15

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_18

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_22
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_25

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_16
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizer_3
Rasterize all rasterizable vector geometries arriving on the Input port, grouping them into output raster features by the provided id, _xmax, _xmin, _ymax, and _ymin attributes, plus the attributes named in the Custom_Attributes_to_Preserve user parameter. For each Output raster, include an _image_base64 attribute containing the base64 encoding of a PNG-formatted version of the raster. This attribute's contents are suitable for use with an HTML ￼￼img tag with inline src.
The vector geometry types currently supported for rasterization are:
Point
Line
Arc
Area
Ellipse
Text
Point Cloud
The following geometry types are not currently rendered (this is likely to change to some kind of planar projection or disaggregation as appropriate in a future enhancement):
Surface
Solid
Collection
Instance
Null
Rasters are passed through ungrouped, and unchanged with the sole exception that they are scaled to the requested dimensions.
IMPORTANT: This transformer must be embedded, not linked, for the calling module (workspace or linked custom transformer) to be properly identified; this is the default when you add it to your workflow.
This transformer is part of a suite that can be used for both data and workflow quality. For the former, data can be tested and exception reports generated from inside any workspace or transformer. For the latter, regression test driver workspaces can call a target workspace or transformer with predefined test data and verify that the results are correct and can be generated without error for both common and edge cases. For issues or questions, please Create an issue here. For the source, including test driver components, please see the Github repository.
Copyright © 2019-2022 by Modern geoSystems, released under this BSD 3-clause license.
Ports
Input
Feed all features that contain geometries to be rasterized.
Output
An ouput feature per group, with all the grouping attributes intact.  Each output feature includes the following additional attribute:
_image_base64 - the base64 encoding of a PNG-formatted version of the raster
Parameters
Specify the parameters for rasterization of the incoming features.
ID
The name of the attribute containing the identifier for each Input feature for grouping purposes.
Name
A name for this Base64PNGRasterizer instance to support the creation of unique temporary filenames.
Default_Pen_Color
The default line drawing color to use for rasterized vector geometries when none is specified.
Default_Fill_Color
The default fill color to use for rasterized vector geometries when none is specified.
_XMAX
The name of the attribute containing the maximum x value for the raster ground extents.
_XMIN
The name of the attribute containing the minimum x value for the raster ground extents.
_YMAX
The name of the attribute containing the maximum y value for the raster ground extents.
_YMIN
The name of the attribute containing the minimum y value for the raster ground extents.
Custom_Attributes_to_Preserve
A space-separated list of custom attributes to include in the grouping of Input features into Output raster features.  These attributes will be included with all Output features.

Parameters:
- All_Attributes_to_Preserve =
- Custom_Attributes_to_Preserve =
- Default_Fill_Color =
- Default_Pen_Color =
- ID =
- Name =
- PNG_Rootname =
- _XMAX =
- _XMIN =
- _YMAX =
- _YMIN =

Input (input)
    -> GeometryExtractor
Note: Save the incoming feature's geometry.
GeometryExtractor
    ATTR = _base64_geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> ImageSizeAttributeCreator
Note: Output the geometry with a standard display width.
ImageSizeAttributeCreator: AttributeCreator
    ATTR_TABLE:
      SET_TO _number_of_columns = 256
      SET_TO _xmin_extent = @Evaluate(@Value(_xmin)-1)
      SET_TO _xmax_extent = @Evaluate(@Value(_xmax)+1)
      SET_TO _ymin_extent = @Evaluate(@Value(_ymin)-1)
      SET_TO _ymax_extent = @Evaluate(@Value(_ymax)+1)
      SET_TO _size_ratio = @Evaluate(@Value(_number_of_columns)/(@Value(_xmax_extent)-@Value(_xmin_extent)))
      SET_TO _number_of_rows = @Evaluate(@round((@Value(_ymax_extent)-@Value(_ymin_extent))*@Value(_size_ratio),0))
      SET_TO _not_rendered_text_string = FME_NULL_VALUE
    -> ValidExtentsTester
ValidExtentsTester: Tester
    BOOL_OP = COMPOSITE
    COMPOSITE_TEST = 1 AND 2 AND 3 AND 4
    TEST_CLAUSE:
      TEST _xmax_extent ATTRIBUTE_HAS_A_VALUE ""
      TEST _xmin_extent ATTRIBUTE_HAS_A_VALUE ""
      TEST _ymax_extent ATTRIBUTE_HAS_A_VALUE ""
      TEST _ymin_extent ATTRIBUTE_HAS_A_VALUE ""
    TEST_MODE = TEST
    PASSED -> ColorsAttributeExposer
    FAILED -> BadExtentsAttributeManager
ColorsAttributeExposer: AttributeExposer
    ATTR_LIST = fme_color,fme_fill_color
    -> Base64PNGRasterizerGeometryFilter [GeometryFilter_Input]
Base64PNGRasterizerGeometryFilter
    ToBeRasterized -> PenColorTester
    ToBeBlank -> SavedColorsAttributeCreator
    ToBeScaledOnly -> RasterScaler
RasterScaler: Scaler
    RASTER_SCALING = Extents
    SCALE_ORIGIN = Center Point
    TEXT_LOC_ONLY = Location and Size
    XSCALE = @Value(_size_ratio)
    YSCALE = @Value(_size_ratio)
    ZSCALE = @Value(_size_ratio)
    SCALED -> ParameterFetcher
BadExtentsAttributeManager: AttributeManager
    ATTR_TABLE:
      SET_TO _number_of_columns = 1
      SET_TO _xmin_extent = 0
      SET_TO _xmax_extent = 1
      SET_TO _ymin_extent = 0
      SET_TO _ymax_extent = 1
      SET_TO _size_ratio = 1
      SET_TO _number_of_rows = 1
      SET_TO _xmax = 1
      SET_TO _xmin = 0
      SET_TO _ymax = 1
      SET_TO _ymin = 0
    -> SavedColorsAttributeCreator
ImageRasterizer
    ALPHA = 1.0
    ANTI_ALIASING = No
    BACKGROUND_ALPHA = 0.0
    BACKGROUND_COLOR = 1,1,1
    COLUMNS = @Value(_number_of_columns)
    FILL_WITH_NODATA = No
    GROUND_EXTENTS_MAX_X = @Value(_xmax_extent)
    GROUND_EXTENTS_MAX_Y = @Value(_ymax_extent)
    GROUND_EXTENTS_MIN_X = @Value(_xmin_extent)
    GROUND_EXTENTS_MIN_Y = @Value(_ymin_extent)
    GROUP_BY = $(All_Attributes_to_Preserve)
    INTERPRETATION_TYPE = RGBA32
    ROWCOL_OR_CELLSIZE = RowsColumns
    ROWS = @Value(_number_of_rows)
    SPECIFY_GROUND_EXTENTS = Specify ground extents
    TOLERANCE = 0.5
    RASTER -> ParameterFetcher
Note: Grab the temporary filename components.
ParameterFetcher
    ATTR_LIST = _PNG_Rootname $(PNG_Rootname) _Name $(Name)
    -> PNGFeatureWriter [Raster]
Note: Save the raster in PNG format.
PNGFeatureWriter: FeatureWriter
    DATASET = $(FME_MF_DIR_ENCODED)Resources/Temp/
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
    Raster -> GeometryReplacer
Note: Restore the incoming feature's geometry.
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_base64_geometry)
    SRS_AXIS_ORDER_DISPLAY = Automatic
    -> Base64PNGRasterizerGeometryFilter_2 [GeometryFilter_Input]
Base64PNGRasterizerGeometryFilter_2
    ToBeRasterized -> AttributeFileReader
    ToBeBlank -> SavedColorsAttributeExposer
    ToBeScaledOnly -> AttributeFileReader
SavedColorsAttributeExposer: AttributeExposer
    ATTR_LIST = _saved_color,_saved_fill_color
    -> FMEColorsAttributeCreator
Note: Restore the saved geometry colors over the blank image colors.
FMEColorsAttributeCreator: AttributeCreator
    ATTR_TABLE:
      SET_TO fme_color = @Value(_saved_color)
      SET_TO fme_fill_color = @Value(_saved_fill_color)
    -> AttributeFileReader
Note: Load the raw PNG binary.
AttributeFileReader
    CHAR_ENCODING = fme-binary
    DEST_ATTR = _image
    FILE_NAME = $(FME_MF_DIR_ENCODED)Resources/Temp/$(PNG_Rootname)_@Value(_Name)_@Value(id).png
    -> ImageBinaryEncoder
Note: Base-64 Encode the PNG binary.
ImageBinaryEncoder: BinaryEncoder
    ATTR_TABLE = _image _image_base64
    ENCODING_TYPE = Base64
    -> FileDeleter
Note: Delete the temporary PNG file.
FileDeleter
    FileToDelete = $(FME_MF_DIR)Resources/Temp/$(PNG_Rootname)_@Value(_Name)_@Value(id).png
    -> Output (output)
Output (output)

Bookmark: Set default colors if not already specified.
PenColorTester: Tester
    BOOL_OP = OR
    COMPOSITE_TEST = 1
    TEST_CLAUSE = TEST fme_color ATTRIBUTE_HAS_A_VALUE ""
    TEST_MODE = TEST
    PASSED -> FillColorTester
    FAILED -> PenColorAttributeCreator
PenColorAttributeCreator: AttributeCreator
    ATTR_TABLE = SET_TO fme_color = $(Default_Pen_Color)
    -> FillColorTester
FillColorTester: Tester
    BOOL_OP = OR
    COMPOSITE_TEST = 1
    TEST_CLAUSE = TEST fme_fill_color ATTRIBUTE_HAS_A_VALUE ""
    TEST_MODE = TEST
    PASSED -> ImageRasterizer
    FAILED -> FillColorAttributeCreator
FillColorAttributeCreator: AttributeCreator
    ATTR_TABLE = SET_TO fme_fill_color = $(Default_Fill_Color)
    -> ImageRasterizer

Bookmark: Set a dummy vertex for a blank image.
SavedColorsAttributeCreator: AttributeCreator
    ATTR_TABLE:
      SET_TO _saved_color = @Value(fme_color)
      SET_TO _saved_fill_color = @Value(fme_fill_color)
    -> BlankImageAttributeCreator
BlankImageAttributeCreator: AttributeCreator
    ATTR_TABLE:
      SET_TO _x = @Evaluate(@round((@Value(_xmax_extent)-@Value(_xmin_extent))/2,0))
      SET_TO _y = @Evaluate(@round((@Value(_ymax_extent)-@Value(_ymin_extent))/2,0))
      SET_TO _not_rendered_text_string = Not Rendered
    -> DummyVertexCreator
DummyVertexCreator: VertexCreator
    MEASURE_TYPE = Continuous
    MODE_NAME = Replace with Point
    XVAL = @Value(_x)
    YVAL = @Value(_y)
    -> BlankFeatureColorSetter
BlankFeatureColorSetter: FeatureColorSetter
    COLOR = $(Default_Fill_Color)
    FILL_COLOR = $(Default_Fill_Color)
    MODE = Fixed
    COLORED -> ImageRasterizer

FME custom transformer FileDeleter_2
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_23
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_13
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_6

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer DatasetValidator
Compare features arriving on Expected and Actual input ports, typically representing different versions of the same dataset.  For example, Expected features may represent expected output for a test, while Actual could be the output of a workflow to be tested to ensure it is working properly.
Expected and Actual features are paired for comparison when they share the same value in their respective id parameter attributes.  Inserted and deleted features are also included in the report, one per line, unless the transformer is configured to ignore them.  Output is generated using the AttributeValidationListPopulator and AttributeValidationHTMLReportGenerator transformers.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2022 by Modern geoSystems, released under this BSD 3-clause license.
Ports
Expected
Feed all features that contain expected values for comparison.
Actual
Feed all features that contain the values to be tested against their expected values.
Report
A single ouput feature enhanced with the following attributes:
html_content{} - The resulting HTML report suitable for output
_no_validation_errors - A flag which, if present, indicates that no validation errors were detected
Output
If differences between paired features were detected, all input features with their discrepancies will be output here.
Parameters
Specify the required yet unknown values for the preceding AttributeValidator.
ID
The name of the attribute containing identifying information to pair the Expected and Actual features.
Validator_Name
The name or prefix of the preceding AttributeValidator.
Attributes_to_Ignore
A comma- or space-separated list of attributes which should not be included in the comparison.  For example, for some use cases, some attributes might be expected to be different between corresponding Expected and Actual features.
Ignore_Unmatched_Features
If set to Yes, ignore inserted or deleted (i.e., unmatched) features.  If set to No (the default), include a line for each inserted or deleted feature in the report.
FME_FEATURE_TYPE
The fme_feature_type attribute.

Parameters:
- Attributes_to_Ignore =
- FME_USER_PARAM_PRIVATE_GRP =
- ID =
- Ignore_Unmatched_Features =
- Transient_Attribute_Names =
- Validator_Name =

Expected (input)
    -> ExpectedBulkAttributeRemover
ExpectedBulkAttributeRemover: BulkAttributeRemover
    ATTR_EXP = $(Transient_Attribute_Names)
    -> ExpectedAttributeRemover
ExpectedAttributeRemover: AttributeRemover
    LIST_ATTRS = $(Attributes_to_Ignore)
    REMOVE_ATTRS = $(Attributes_to_Ignore)
    -> ChangeDetector [ORIGINAL]
    -> Junction_7
Note: ExpectedActualFeatureJoiner : Right
Junction_7
    -> Junction_8
Note: ExpectedAttributeRemover : Output
Junction_8
    -> ExpectedActualFeatureJoiner [RIGHT]
Actual (input)
    -> ActualBulkAttributeRemover
ActualBulkAttributeRemover: BulkAttributeRemover
    ATTR_EXP = $(Transient_Attribute_Names)
    -> ActualAttributeRemover
ActualAttributeRemover: AttributeRemover
    LIST_ATTRS = $(Attributes_to_Ignore)
    REMOVE_ATTRS = $(Attributes_to_Ignore)
    -> ChangeDetector [REVISED]
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCH_STRATEGY = Match All Attributes
    PREEMPTIVE_ATTRS = id
    UNCHANGED_OUTPUT = Output Original
    UPDATED_LIST_NAME = _differences
    UPDATED -> ListElementCounter
    INSERTED -> ListElementCounter
    DELETED -> ListElementCounter
    UNCHANGED -> ListElementCounter
ListElementCounter
    CNT_ATTR = _differences_element_count
    LIST_NAME = _differences{}
    -> ListExploder
ListExploder
    ATTR_ACCUM_MODE = Prefix List Attributes
    INCOMING_PREFIX = _differences.
    INDEX_ATTR = _element_index
    LIST_ATTR = _differences{}
    ELEMENTS -> NameAttributeFilter
    <REJECTED> -> UnchangedFeatureTester
NameAttributeFilter: AttributeFilter
    ATTR_NAME = _differences.attributeName
    ATTR_VALUES = <Empty>,<Missing>,<Null>,<Unfiltered>,geometryObject
    <UNFILTERED> -> AttributeStringConcatenator
    geometryObject -> ActualBoundsExtractor
Note: Generate attribute difference message text.
AttributeStringConcatenator: StringConcatenator
    ACTION = Create New Attribute
    PARM_LINE = fme_basicstring:10%34%1%27:Attribute @Value(_differences.attributeName) @Value(_differences.action)
    VAL_ATTR = _fme_validation_message
    -> ValuesAttributeCreator
Note: Generate attribute values text.
ValuesAttributeCreator: AttributeCreator
    ATTR_TABLE:
      SET_TO _fme_validation_expected_value = @Value(_differences.originalValue)
      SET_TO _fme_validation_actual_value = @Value(_differences.revisedValue)
    -> Sampler
ActualBoundsExtractor: BoundsExtractor
    XMAX = _xmax_2
    XMIN = _xmin_2
    YMAX = _ymax_2
    YMIN = _ymin_2
    ZMAX = _zmax_2
    ZMIN = _zmin_2
    -> ActualGeometryExtractor
Note: Save the actual geometry before it's clobbered while we process the expected geometry.
ActualGeometryExtractor: GeometryExtractor
    ATTR = _geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> ExpectedActualFeatureJoiner [LEFT]
ExpectedActualFeatureJoiner: FeatureJoiner
    ATTR_CONFLICT_RES = Use Right
    GEOMETRY_HANDLING = Use Right
    GROUP_BY = id
    JOIN_KEYS = id id AUTO
    JOIN_MODE = Inner
    JOINED -> ExpectedBoundsExtractor
ExpectedBoundsExtractor: BoundsExtractor
    XMAX = _xmax_1
    XMIN = _xmin_1
    YMAX = _ymax_1
    YMIN = _ymin_1
    ZMAX = _zmax_1
    ZMIN = _zmin_1
    -> BoundsAttributeCreator
ExpectedBase64PNGRasterizer: Base64PNGRasterizer_4
    All_Attributes_to_Preserve:
      import fme
      import re


      # Initialize the grouping attribute list with all the existing attribute parameters and all internally-generated attributes.
      result = 'id _xmax _xmax_extent _xmin _xmin_extent _ymax _ymax_extent _ymin _ymin_extent _base64_geometry _number_of_columns _number_of_rows _saved_color _saved_fill_color _size_ratio _x _y fme_color fme_feature_type fme_fill_color fme_rotation fme_text_size fme_text_string _not_rendered_text_string'

      # Add any custom attributes specified in the transformer parameters.
      sample_user_parameter = next(name for name in FME_MacroValues.keys() if re.search(r'_(ID|_[XY]MAX|_[XY]MIN)', name) and not name.startswith('FME_'))
      parameter_prefix = '_'.join([component for component in sample_user_parameter.split('_') if len(component) > 0][0:-1])
      if len(fme.macroValues[parameter_prefix + '_Custom_Attributes_to_Preserve']) > 0:
          result += ' ' + fme.macroValues[parameter_prefix + '_Custom_Attributes_to_Preserve']

      return result
    Custom_Attributes_to_Preserve = _fme_validation_expected_value _geometry
    Default_Fill_Color = 1,1,1,0
    Default_Pen_Color = 0,0,0,1
    ID = @Value(id)
    Name = expected
    _XMAX = @Value(_xmax)
    _XMIN = @Value(_xmin)
    _YMAX = @Value(_ymax)
    _YMIN = @Value(_ymin)
    -> ExpectedValueAttributeCreator
Note: Generate embedded image tag for the expected geometry.
ExpectedValueAttributeCreator: AttributeCreator
    ATTR_TABLE = SET_TO _fme_validation_expected_value = FME_CONDITIONAL:DEFAULT_VALUE'<img src="data:image/png;base64, @Value(_image_base64)" alt="Expected Geometry" width="256"/>'BOOL_OP;OR;COMPOSITE_TEST;1;TEST _not_rendered_text_string ATTRIBUTE_HAS_A_VALUE _FME_BLANK_STRING_'@Value(_not_rendered_text_string)'FME_NUM_CONDITIONS2___
    -> ActualGeometryReplacer
Note: Restore the actual geometry now that we've processed the expected geometry.
ActualGeometryReplacer: GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = No
    SOURCE = @Value(_geometry)
    SRS_AXIS_ORDER_DISPLAY = Automatic
    -> ActualBase64PNGRasterizer
ActualBase64PNGRasterizer: Base64PNGRasterizer_4
    All_Attributes_to_Preserve:
      import fme
      import re


      # Initialize the grouping attribute list with all the existing attribute parameters and all internally-generated attributes.
      result = 'id _xmax _xmax_extent _xmin _xmin_extent _ymax _ymax_extent _ymin _ymin_extent _base64_geometry _number_of_columns _number_of_rows _saved_color _saved_fill_color _size_ratio _x _y fme_color fme_feature_type fme_fill_color fme_rotation fme_text_size fme_text_string _not_rendered_text_string'

      # Add any custom attributes specified in the transformer parameters.
      sample_user_parameter = next(name for name in FME_MacroValues.keys() if re.search(r'_(ID|_[XY]MAX|_[XY]MIN)', name) and not name.startswith('FME_'))
      parameter_prefix = '_'.join([component for component in sample_user_parameter.split('_') if len(component) > 0][0:-1])
      if len(fme.macroValues[parameter_prefix + '_Custom_Attributes_to_Preserve']) > 0:
          result += ' ' + fme.macroValues[parameter_prefix + '_Custom_Attributes_to_Preserve']

      return result
    Custom_Attributes_to_Preserve = _fme_validation_expected_value _geometry
    Default_Fill_Color = 1,1,1,0
    Default_Pen_Color = 0,0,0,1
    ID = @Value(id)
    Name = actual
    _XMAX = @Value(_xmax)
    _XMIN = @Value(_xmin)
    _YMAX = @Value(_ymax)
    _YMIN = @Value(_ymin)
    -> ActualValueAttributeCreator
Note: Generate embedded image tag for the actual geometry.
ActualValueAttributeCreator: AttributeCreator
    ATTR_TABLE = SET_TO _fme_validation_actual_value = FME_CONDITIONAL:DEFAULT_VALUE'<img src="data:image/png;base64, @Value(_image_base64)" alt="Actual Geometry" width="256"/>'BOOL_OP;OR;COMPOSITE_TEST;1;TEST _not_rendered_text_string ATTRIBUTE_HAS_A_VALUE _FME_BLANK_STRING_'@Value(_not_rendered_text_string)'FME_NUM_CONDITIONS2___
    -> GeometryStringConcatenator
Note: Generate geometry difference message text.
GeometryStringConcatenator: StringConcatenator
    ACTION = Create New Attribute
    PARM_LINE = fme_basicstring:9%27:Geometry @Value(_differences.action)
    VAL_ATTR = _fme_validation_message
    -> Junction_3
Note: Sampler : Input
Junction_3
    -> Junction_4
Note: GeometryStringConcatenator : Output
Junction_4
    -> Sampler
Sampler
    GROUP_BY = id
    RATE = 1
    SAMPLE_MODE = No
    SAMPLE_TYPE_LONG = First N Features
    SAMPLED -> GeometryExtractor
    NOT_SAMPLED -> Aggregator
UnchangedFeatureTester: Tester
    BOOL_OP = OR
    COMPOSITE_TEST = 1
    TEST_CLAUSE = TEST fme_db_operation NOT_ATTRIBUTE_HAS_A_VALUE ""
    TEST_MODE = TEST
    PASSED -> Junction
    FAILED -> FeatureStringConcatenator
Note: ListRenamer : Input
Junction
    -> Junction_2
Note: UnchangedFeatureTester : Passed
Junction_2
    -> MessageListRenamer
FeatureStringConcatenator: StringConcatenator
    ACTION = Create New Attribute
    PARM_LINE = fme_basicstring:8%24%2:Feature @Value(fme_db_operation)ED
    VAL_ATTR = _fme_validation_message
    -> IncludeUnmatchedFeaturesTester
IncludeUnmatchedFeaturesTester: Tester
    BOOL_OP = OR
    COMPOSITE_TEST = 1
    TEST_CLAUSE = TEST $(Ignore_Unmatched_Features) = No
    TEST_MODE = TEST
    PASSED -> Junction_5
    FAILED -> Junction_9
Note: GeometryExtractor : Input
Junction_5
    -> Junction_6
Note: IncludeUnmatchedFeaturesTester : Passed
Junction_6
    -> GeometryExtractor
GeometryExtractor
    ATTR = _geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = Yes
    -> Aggregator
Aggregator
    ACCUM_ATTRS_NAME = Use Attributes From One Feature
    GROUP_BY = id
    LIST_ATTRS_TO_INCLUDE = _fme_validation_message _fme_validation_actual_value _fme_validation_expected_value
    LIST_NAME = _fme_validation_message_list
    MODE = Attributes Only
    SEP = ,
    AGGREGATE -> GeometryReplacer
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_geometry)
    SRS_AXIS_ORDER_DISPLAY = Automatic
    -> MessageListRenamer
Note: MessageListRenamer : Input
Junction_9
    -> Junction_10
Note: IncludeUnmatchedFeaturesTester : Failed
Junction_10
    -> MessageListRenamer
AttributeValidationListPopulator
    Validator_Name = $(Validator_Name)
    -> Output (output)
    -> AttributeValidationHTMLReportGenerator
AttributeValidationHTMLReportGenerator
    _FEATURE_ID = @Value(id)
    -> Report (output)
Report (output)
Output (output)

Bookmark: Consolidate extents.
BoundsAttributeCreator: AttributeCreator
    ATTR_TABLE:
      SET_TO _xmin = @Evaluate(@min(@Value(_xmin_1),@Value(_xmin_2)))
      SET_TO _xmax = @Evaluate(@max(@Value(_xmax_1),@Value(_xmax_2)))
      SET_TO _ymin = @Evaluate(@min(@Value(_ymin_1),@Value(_ymin_2)))
      SET_TO _ymax = @Evaluate(@max(@Value(_ymax_1),@Value(_ymax_2)))
      SET_TO _fme_validation_expected_value
    -> BoundsAttributeRemover
BoundsAttributeRemover: AttributeRemover
    REMOVE_ATTRS = _xmax_1,_xmax_2,_xmin_1,_xmin_2,_ymax_1,_ymax_2,_ymin_1,_ymin_2,_zmax_1,_zmax_2,_zmin_1,_zmin_2
    -> ExpectedBase64PNGRasterizer

Bookmark: Promote report column output lists.
MessageListRenamer: ListRenamer
    LEAVE_ORIG = No
    LIST_ACTION = Rename
    LIST_COMPONENT_NAMES = _fme_validation_message_list{},_fme_validation_message_list{},_fme_validation_message,
    LIST_NAME = _fme_validation_message_list{}._fme_validation_message
    -> ExpectedValueMessageListRenamer
ExpectedValueMessageListRenamer: ListRenamer
    LEAVE_ORIG = No
    LIST_ACTION = Rename
    LIST_COMPONENT_NAMES = _fme_validation_message_list{},_fme_validation_expected_value_list{},_fme_validation_expected_value,
    LIST_NAME = _fme_validation_message_list{}._fme_validation_expected_value
    -> ActualValueMessageListRenamer
ActualValueMessageListRenamer: ListRenamer
    LEAVE_ORIG = No
    LIST_ACTION = Rename
    LIST_COMPONENT_NAMES = _fme_validation_message_list{},_fme_validation_actual_value_list{},_fme_validation_actual_value,
    LIST_NAME = _fme_validation_message_list{}._fme_validation_actual_value
    -> AttributeValidationListPopulator

FME custom transformer Base64PNGRasterizerGeometryFilter_23

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_9

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_12
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer AttributeValidationListPopulator
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer Base64PNGRasterizerGeometryFilter_24

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizer_4
Rasterize all rasterizable vector geometries arriving on the Input port, grouping them into output raster features by the provided id, _xmax, _xmin, _ymax, and _ymin attributes, plus the attributes named in the Custom_Attributes_to_Preserve user parameter. For each Output raster, include an _image_base64 attribute containing the base64 encoding of a PNG-formatted version of the raster. This attribute's contents are suitable for use with an inline HTML ￼￼ tag.
The vector geometry types currently supported for rasterization are:
Point
Line
Arc
Area
Ellipse
Text
Point Cloud
The following geometry types are not currently rendered (this is likely to change to some kind of planar projection or disaggregation as appropriate in a future enhancement):
Surface
Solid
Collection
Instance
Null
Rasters are passed through ungrouped, and unchanged with the sole exception that they are scaled to the requested dimensions.
IMPORTANT: This transformer must be embedded, not linked, for the calling module (workspace or linked custom transformer) to be properly identified; this is the default when you add it to your workflow.
This transformer is part of a suite that can be used for both data and workflow quality. For the former, data can be tested and exception reports generated from inside any workspace or transformer. For the latter, regression test driver workspaces can call a target workspace or transformer with predefined test data and verify that the results are correct and can be generated without error for both common and edge cases. For issues or questions, please Create an issue here. For the source, including test driver components, please see the Github repository.
Copyright © 2019-2022 by Modern geoSystems, released under this BSD 3-clause license.
Ports
Input
Feed all features that contain geometries to be rasterized.
Output
An ouput feature per group, with all the grouping attributes intact.  Each output feature includes the following additional attribute:
_image_base64 - the base64 encoding of a PNG-formatted version of the raster
Parameters
Specify the parameters for rasterization of the incoming features.
ID
The name of the attribute containing the identifier for each Input feature for grouping purposes.
Name
A name for this Base64PNGRasterizer instance to support the creation of unique temporary filenames.
Default_Pen_Color
The default line drawing color to use for rasterized vector geometries when none is specified.
Default_Fill_Color
The default fill color to use for rasterized vector geometries when none is specified.
_XMAX
The name of the attribute containing the maximum x value for the raster ground extents.
_XMIN
The name of the attribute containing the minimum x value for the raster ground extents.
_YMAX
The name of the attribute containing the maximum y value for the raster ground extents.
_YMIN
The name of the attribute containing the minimum y value for the raster ground extents.
Custom_Attributes_to_Preserve
A space-separated list of custom attributes to include in the grouping of Input features into Output raster features.  These attributes will be included with all Output features.

Parameters:
- All_Attributes_to_Preserve =
- Custom_Attributes_to_Preserve =
- Default_Fill_Color =
- Default_Pen_Color =
- ID =
- Name =
- _XMAX =
- _XMIN =
- _YMAX =
- _YMIN =

Input (input)
    -> GeometryExtractor
Note: Save the incoming feature's geometry.
GeometryExtractor
    ATTR = _base64_geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> ImageSizeAttributeCreator
Note: Output the geometry with a standard display width.
ImageSizeAttributeCreator: AttributeCreator
    ATTR_TABLE:
      SET_TO _number_of_columns = 256
      SET_TO _xmin_extent = @Evaluate(@Value(_xmin)-1)
      SET_TO _xmax_extent = @Evaluate(@Value(_xmax)+1)
      SET_TO _ymin_extent = @Evaluate(@Value(_ymin)-1)
      SET_TO _ymax_extent = @Evaluate(@Value(_ymax)+1)
      SET_TO _size_ratio = @Evaluate(@Value(_number_of_columns)/(@Value(_xmax_extent)-@Value(_xmin_extent)))
      SET_TO _number_of_rows = @Evaluate(@round((@Value(_ymax_extent)-@Value(_ymin_extent))*@Value(_size_ratio),0))
      SET_TO _not_rendered_text_string = FME_NULL_VALUE
    -> ValidExtentsTester
ValidExtentsTester: Tester
    BOOL_OP = COMPOSITE
    COMPOSITE_TEST = 1 AND 2 AND 3 AND 4
    TEST_CLAUSE:
      TEST _xmax_extent ATTRIBUTE_HAS_A_VALUE ""
      TEST _xmin_extent ATTRIBUTE_HAS_A_VALUE ""
      TEST _ymax_extent ATTRIBUTE_HAS_A_VALUE ""
      TEST _ymin_extent ATTRIBUTE_HAS_A_VALUE ""
    TEST_MODE = TEST
    PASSED -> ColorsAttributeExposer
    FAILED -> BadExtentsAttributeManager
ColorsAttributeExposer: AttributeExposer
    ATTR_LIST = fme_color,fme_fill_color
    -> Base64PNGRasterizerGeometryFilter [GeometryFilter_Input]
Base64PNGRasterizerGeometryFilter
    ToBeRasterized -> PenColorTester
    ToBeBlank -> SavedColorsAttributeCreator
    ToBeScaledOnly -> RasterScaler
RasterScaler: Scaler
    RASTER_SCALING = Extents
    SCALE_ORIGIN = Center Point
    TEXT_LOC_ONLY = Location and Size
    XSCALE = @Value(_size_ratio)
    YSCALE = @Value(_size_ratio)
    ZSCALE = @Value(_size_ratio)
    SCALED -> Base64PNGRasterizerGeometryFilter_2 [GeometryFilter_Input]
BadExtentsAttributeManager: AttributeManager
    ATTR_TABLE:
      SET_TO _number_of_columns = 1
      SET_TO _xmin_extent = 0
      SET_TO _xmax_extent = 1
      SET_TO _ymin_extent = 0
      SET_TO _ymax_extent = 1
      SET_TO _size_ratio = 1
      SET_TO _number_of_rows = 1
      SET_TO _xmax = 1
      SET_TO _xmin = 0
      SET_TO _ymax = 1
      SET_TO _ymin = 0
    -> SavedColorsAttributeCreator
ImageRasterizer
    ALPHA = 1.0
    ANTI_ALIASING = No
    BACKGROUND_ALPHA = 0.0
    BACKGROUND_COLOR = 1,1,1
    COLUMNS = @Value(_number_of_columns)
    FILL_WITH_NODATA = No
    GROUND_EXTENTS_MAX_X = @Value(_xmax_extent)
    GROUND_EXTENTS_MAX_Y = @Value(_ymax_extent)
    GROUND_EXTENTS_MIN_X = @Value(_xmin_extent)
    GROUND_EXTENTS_MIN_Y = @Value(_ymin_extent)
    GROUP_BY = $(All_Attributes_to_Preserve)
    INTERPRETATION_TYPE = RGBA32
    ROWCOL_OR_CELLSIZE = RowsColumns
    ROWS = @Value(_number_of_rows)
    SPECIFY_GROUND_EXTENTS = Specify ground extents
    TOLERANCE = 0.5
    RASTER -> Base64PNGRasterizerGeometryFilter_2 [GeometryFilter_Input]
Base64PNGRasterizerGeometryFilter_2
    ToBeRasterized -> RasterExtractor
    ToBeBlank -> SavedColorsAttributeExposer
    ToBeScaledOnly -> RasterExtractor
SavedColorsAttributeExposer: AttributeExposer
    ATTR_LIST = _saved_color,_saved_fill_color
    -> FMEColorsAttributeCreator
Note: Restore the saved geometry colors over the blank image colors.
FMEColorsAttributeCreator: AttributeCreator
    ATTR_TABLE:
      SET_TO fme_color = @Value(_saved_color)
      SET_TO fme_fill_color = @Value(_saved_fill_color)
    -> RasterExtractor
Note: Extract a PNG-formatted image binary attribute.
RasterExtractor
    RASTER_BLOB_ATTR = _image
    RASTER_FORMAT = PNGRASTER
    RASTER_FORMAT_ATTR = _rasterFormatName
    -> ImageBinaryEncoder
Note: Base-64 Encode the PNG binary.
ImageBinaryEncoder: BinaryEncoder
    ATTR_TABLE = _image _image_base64
    ENCODING_TYPE = Base64
    -> Output (output)
Output (output)

Bookmark: Set default colors if not already specified.
PenColorTester: Tester
    BOOL_OP = OR
    COMPOSITE_TEST = 1
    TEST_CLAUSE = TEST fme_color ATTRIBUTE_HAS_A_VALUE ""
    TEST_MODE = TEST
    PASSED -> FillColorTester
    FAILED -> PenColorAttributeCreator
PenColorAttributeCreator: AttributeCreator
    ATTR_TABLE = SET_TO fme_color = $(Default_Pen_Color)
    -> FillColorTester
FillColorTester: Tester
    BOOL_OP = OR
    COMPOSITE_TEST = 1
    TEST_CLAUSE = TEST fme_fill_color ATTRIBUTE_HAS_A_VALUE ""
    TEST_MODE = TEST
    PASSED -> ImageRasterizer
    FAILED -> FillColorAttributeCreator
FillColorAttributeCreator: AttributeCreator
    ATTR_TABLE = SET_TO fme_fill_color = $(Default_Fill_Color)
    -> ImageRasterizer

Bookmark: Set a dummy vertex for a blank image.
SavedColorsAttributeCreator: AttributeCreator
    ATTR_TABLE:
      SET_TO _saved_color = @Value(fme_color)
      SET_TO _saved_fill_color = @Value(fme_fill_color)
    -> BlankImageAttributeCreator
BlankImageAttributeCreator: AttributeCreator
    ATTR_TABLE:
      SET_TO _x = @Evaluate(@round((@Value(_xmax_extent)-@Value(_xmin_extent))/2,0))
      SET_TO _y = @Evaluate(@round((@Value(_ymax_extent)-@Value(_ymin_extent))/2,0))
      SET_TO _not_rendered_text_string = Not Rendered
    -> DummyVertexCreator
DummyVertexCreator: VertexCreator
    MEASURE_TYPE = Continuous
    MODE_NAME = Replace with Point
    XVAL = @Value(_x)
    YVAL = @Value(_y)
    -> BlankFeatureColorSetter
BlankFeatureColorSetter: FeatureColorSetter
    COLOR = $(Default_Fill_Color)
    FILL_COLOR = $(Default_Fill_Color)
    MODE = Fixed
    COLORED -> ImageRasterizer

FME custom transformer FileDeleter_24
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_8
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer AttributeValidationListPopulator_4
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer FileDeleter_18
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_3
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_21
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer FileDeleter_10
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_19

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_17
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_12

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer FileDeleter_14
Delete specified file - not using Python, but rather the FeatureWriter - Copy File approach to remove the file. 
Image by OpenClipart-Vectors from Pixabay

Parameters:
- FileToDelete =

Input (input)
    -> AttributeManager
AttributeManager
    ATTR_TABLE:
      SET_TO filecopy_source_dataset = $(FileToDelete)
      SET_TO filecopy_dest_dataset
      SET_TO filecopy_dest_filename = nul
    -> FeatureWriter [filecopy]
FeatureWriter
    DATASET = c:\temp
    DATASET_ATTR = _dataset
    FEATURE_TYPE_LIST_ATTR = _feature_type
    FILECOPY_COORDINATE_SYSTEM_GRANULARITY = FEATURE
    FILECOPY_COPY_SOURCE_DIRECTORY = NO
    FILECOPY_COPY_SUBDIRECTORIES = YES
    FILECOPY_DESTINATION_DATASETTYPE_VALIDATION = Yes
    FILECOPY_FAIL_INVALID_DESTINATION = NO
    FILECOPY_FAIL_NONEXISTENT_SOURCE = NO
    FILECOPY_FILE_OPERATION = MOVE
    FILECOPY_MIME_TYPE = text/plain
    FILECOPY_OVERWRITE_FILE = YES
    FORMAT = FILECOPY
    TOTAL_FEATURES_WRITTEN_ATTR = _total_features_written
    filecopy -> Output (output)
Output (output)

FME custom transformer Base64PNGRasterizerGeometryFilter_22

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_7

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_21

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer Base64PNGRasterizerGeometryFilter_11

GeometryFilter_Input (input)
    -> GeometryFilter
Note: We don't currently support some geometry types, nor do we need to rasterize any geometries that are already rasters.
GeometryFilter
    BREAK_AGG = No
    GEOM_PORT_NAMES = Point Line Arc Area Ellipse Text Raster "Point Cloud" Surface Solid Collection Null Instance
    POINT -> ToBeRasterized (output)
    LINE -> ToBeRasterized (output)
    ARC -> ToBeRasterized (output)
    AREA -> ToBeRasterized (output)
    ELLIPSE -> ToBeRasterized (output)
    TEXT -> ToBeRasterized (output)
    RASTER -> ToBeScaledOnly (output)
    POINTCLOUD -> ToBeRasterized (output)
    SURFACE -> ToBeBlank (output)
    SOLID -> ToBeBlank (output)
    COLLECTION -> ToBeBlank (output)
    NULL -> ToBeBlank (output)
    INSTANCE -> ToBeBlank (output)
    <UNFILTERED> -> ToBeBlank (output)
ToBeRasterized (output)
ToBeBlank (output)
ToBeScaledOnly (output)

FME custom transformer AttributeValidationListPopulator_2
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer Base64PNGRasterizer_2
Rasterize all rasterizable vector geometries arriving on the Input port, grouping them into output raster features by the provided id, _xmax, _xmin, _ymax, and _ymin attributes, plus the attributes named in the Custom_Attributes_to_Preserve user parameter. For each Output raster, include an _image_base64 attribute containing the base64 encoding of a PNG-formatted version of the raster. This attribute's contents are suitable for use with an inline HTML ￼<img> tag. The vector geometry types currently supported for rasterization are:
Point
Line
Arc
Area
Ellipse
Text
Point Cloud
The following geometry types are currently rendered as single points in the Default_Fill_Color on the output rasters (this is likely to change to some kind of planar projection or disaggregation as appropriate in a future enhancement):
Surface
Solid
Collection
Instance
Null
Rasters are passed through ungrouped, and unchanged with the sole exception that they are scaled to the requested dimensions.
IMPORTANT: This transformer must be embedded, not linked, for the calling module (workspace or linked custom transformer) to be properly identified; this is the default when you add it to your workflow.
This transformer is part of a suite that can be used for both data and workflow quality. For the former, data can be tested and exception reports generated from inside any workspace or transformer. For the latter, regression test driver workspaces can call a target workspace or transformer with predefined test data and verify that the results are correct and can be generated without error for both common and edge cases.
For issues or questions, please Create an issue here. For the source, including test driver components, please see the Github repository.
Copyright © 2019-2022 by Modern geoSystems, released under this BSD 3-clause license.
Ports
Input
Feed all features that contain geometries to be rasterized.
Output
An ouput feature per group, with all the grouping attributes intact.  Each output feature includes the following additional attribute:
_image_base64 - the base64 encoding of a PNG-formatted version of the raster
Parameters
Specify the parameters for rasterization of the incoming features.
ID
The name of the attribute containing the identifier for each Input feature for grouping purposes.
Name
A name for this Base64PNGRasterizer instance to support the creation of unique temporary filenames.
Default_Pen_Color
The default line drawing color to use for rasterized vector geometries when none is specified.
Default_Fill_Color
The default fill color to use for rasterized vector geometries when none is specified.
_XMAX
The name of the attribute containing the maximum x value for the raster ground extents.
_XMIN
The name of the attribute containing the minimum x value for the raster ground extents.
_YMAX
The name of the attribute containing the maximum y value for the raster ground extents.
_YMIN
The name of the attribute containing the minimum y value for the raster ground extents.
Custom_Attributes_to_Preserve
A space-separated list of custom attributes to include in the grouping of Input features into Output raster features.  These attributes will be included with all Output features.

Parameters:
- All_Attributes_to_Preserve =
- Custom_Attributes_to_Preserve =
- Default_Fill_Color =
- Default_Pen_Color =
- ID =
- Name =
- PNG_Rootname =
- _XMAX =
- _XMIN =
- _YMAX =
- _YMIN =

Input (input)
    -> GeometryExtractor
Note: Save the incoming feature's geometry.
GeometryExtractor
    ATTR = _base64_geometry
    GENERATE_GEOMETRY_IDS = No
    KIND_LONG = FME Binary
    OGCVERSION = 1.2
    OGC_WKT_PRECISION_DISPLAY = 64-bit
    OGEOSMS_URL_PREFIX = http://maps.google.com/?q=
    PREFER_POLYGON_OVER_SURFACE = No
    REMOVE_GEOMETRY = No
    -> ImageSizeAttributeCreator
Note: Output the geometry with a standard display width.
ImageSizeAttributeCreator: AttributeCreator
    ATTR_TABLE:
      SET_TO _number_of_columns = 256
      SET_TO _xmin_extent = @Evaluate(@Value(_xmin)-1)
      SET_TO _xmax_extent = @Evaluate(@Value(_xmax)+1)
      SET_TO _ymin_extent = @Evaluate(@Value(_ymin)-1)
      SET_TO _ymax_extent = @Evaluate(@Value(_ymax)+1)
      SET_TO _size_ratio = @Evaluate(@Value(_number_of_columns)/(@Value(_xmax_extent)-@Value(_xmin_extent)))
      SET_TO _number_of_rows = @Evaluate(@round((@Value(_ymax_extent)-@Value(_ymin_extent))*@Value(_size_ratio),0))
    -> ValidExtentsTester
ValidExtentsTester: Tester
    BOOL_OP = COMPOSITE
    COMPOSITE_TEST = 1 AND 2 AND 3 AND 4
    TEST_CLAUSE:
      TEST _xmax_extent ATTRIBUTE_HAS_A_VALUE ""
      TEST _xmin_extent ATTRIBUTE_HAS_A_VALUE ""
      TEST _ymax_extent ATTRIBUTE_HAS_A_VALUE ""
      TEST _ymin_extent ATTRIBUTE_HAS_A_VALUE ""
    TEST_MODE = TEST
    PASSED -> ColorsAttributeExposer
    FAILED -> BadExtentsAttributeManager
ColorsAttributeExposer: AttributeExposer
    ATTR_LIST = fme_color,fme_fill_color
    -> Base64PNGRasterizerGeometryFilter [GeometryFilter_Input]
Base64PNGRasterizerGeometryFilter
    ToBeRasterized -> PenColorTester
    ToBeBlank -> SavedColorsAttributeCreator
    ToBeScaledOnly -> RasterScaler
RasterScaler: Scaler
    RASTER_SCALING = Extents
    SCALE_ORIGIN = Center Point
    TEXT_LOC_ONLY = Location and Size
    XSCALE = @Value(_size_ratio)
    YSCALE = @Value(_size_ratio)
    ZSCALE = @Value(_size_ratio)
    SCALED -> ParameterFetcher
BadExtentsAttributeManager: AttributeManager
    ATTR_TABLE:
      SET_TO _number_of_columns = 1
      SET_TO _xmin_extent = 0
      SET_TO _xmax_extent = 1
      SET_TO _ymin_extent = 0
      SET_TO _ymax_extent = 1
      SET_TO _size_ratio = 1
      SET_TO _number_of_rows = 1
      SET_TO _xmax = 1
      SET_TO _xmin = 0
      SET_TO _ymax = 1
      SET_TO _ymin = 0
    -> SavedColorsAttributeCreator
ImageRasterizer
    ALPHA = 1.0
    ANTI_ALIASING = No
    BACKGROUND_ALPHA = 0.0
    BACKGROUND_COLOR = 1,1,1
    COLUMNS = @Value(_number_of_columns)
    FILL_WITH_NODATA = No
    GROUND_EXTENTS_MAX_X = @Value(_xmax_extent)
    GROUND_EXTENTS_MAX_Y = @Value(_ymax_extent)
    GROUND_EXTENTS_MIN_X = @Value(_xmin_extent)
    GROUND_EXTENTS_MIN_Y = @Value(_ymin_extent)
    GROUP_BY = $(All_Attributes_to_Preserve)
    INTERPRETATION_TYPE = RGBA32
    ROWCOL_OR_CELLSIZE = RowsColumns
    ROWS = @Value(_number_of_rows)
    SPECIFY_GROUND_EXTENTS = Specify ground extents
    TOLERANCE = 0.5
    RASTER -> ParameterFetcher
Note: Grab the temporary filename components.
ParameterFetcher
    ATTR_LIST = _PNG_Rootname $(PNG_Rootname) _Name $(Name)
    -> PNGFeatureWriter [Raster]
Note: Save the raster in PNG format.
PNGFeatureWriter: FeatureWriter
    DATASET = $(FME_MF_DIR_ENCODED)Resources/Temp/
    DATASET_ATTR = _dataset
    FEATURE_TYPE_LIST_ATTR = _feature_types
    FORMAT = PNGRASTER
    PNGRASTER_COORDINATE_SYSTEM_GRANULARITY = FEATURE
    TOTAL_FEATURES_WRITTEN_ATTR = _total_features_written
    Raster -> GeometryReplacer
Note: Restore the incoming feature's geometry.
GeometryReplacer
    ELLIPSOID_NAME = WGS84
    KIND_LONG = FME Binary
    LETTERING = WGS84
    MSSQL_FORMAT_CHOICE = Geometry
    OGC_WKT_PRECISION_DISPLAY = 64-bit
    OUTPUT_POINT_DISPLAY = Point
    REMOVE_ATTRIBUTE = Yes
    SOURCE = @Value(_base64_geometry)
    SRS_AXIS_ORDER_DISPLAY = Automatic
    -> Base64PNGRasterizerGeometryFilter_2 [GeometryFilter_Input]
Base64PNGRasterizerGeometryFilter_2
    ToBeRasterized -> AttributeFileReader
    ToBeBlank -> SavedColorsAttributeExposer
    ToBeScaledOnly -> AttributeFileReader
SavedColorsAttributeExposer: AttributeExposer
    ATTR_LIST = _saved_color,_saved_fill_color
    -> FMEColorsAttributeCreator
Note: Restore the saved geometry colors over the blank image colors.
FMEColorsAttributeCreator: AttributeCreator
    ATTR_TABLE:
      SET_TO fme_color = @Value(_saved_color)
      SET_TO fme_fill_color = @Value(_saved_fill_color)
    -> AttributeFileReader
Note: Load the raw PNG binary.
AttributeFileReader
    CHAR_ENCODING = fme-binary
    DEST_ATTR = _image
    FILE_NAME = $(FME_MF_DIR_ENCODED)Resources/Temp/$(PNG_Rootname)_@Value(_Name)_@Value(id).png
    -> ImageBinaryEncoder
Note: Base-64 Encode the PNG binary.
ImageBinaryEncoder: BinaryEncoder
    ATTR_TABLE = _image _image_base64
    ENCODING_TYPE = Base64
    -> FileDeleter
Note: Delete the temporary PNG file.
FileDeleter
    FileToDelete = $(FME_MF_DIR)Resources/Temp/$(PNG_Rootname)_@Value(_Name)_@Value(id).png
    -> Output (output)
Output (output)

Bookmark: Set default colors if not already specified.
PenColorTester: Tester
    BOOL_OP = OR
    COMPOSITE_TEST = 1
    TEST_CLAUSE = TEST fme_color ATTRIBUTE_HAS_A_VALUE ""
    TEST_MODE = TEST
    PASSED -> FillColorTester
    FAILED -> PenColorAttributeCreator
PenColorAttributeCreator: AttributeCreator
    ATTR_TABLE = SET_TO fme_color = $(Default_Pen_Color)
    -> FillColorTester
FillColorTester: Tester
    BOOL_OP = OR
    COMPOSITE_TEST = 1
    TEST_CLAUSE = TEST fme_fill_color ATTRIBUTE_HAS_A_VALUE ""
    TEST_MODE = TEST
    PASSED -> ImageRasterizer
    FAILED -> FillColorAttributeCreator
FillColorAttributeCreator: AttributeCreator
    ATTR_TABLE = SET_TO fme_fill_color = $(Default_Fill_Color)
    -> ImageRasterizer

Bookmark: Set a dummy vertex for a blank image.
SavedColorsAttributeCreator: AttributeCreator
    ATTR_TABLE:
      SET_TO _saved_color = @Value(fme_color)
      SET_TO _saved_fill_color = @Value(fme_fill_color)
    -> DummyLocationAttributeCreator
DummyLocationAttributeCreator: AttributeCreator
    ATTR_TABLE:
      SET_TO _x = @Evaluate(@round((@Value(_xmax_extent)-@Value(_xmin_extent))/2,0))
      SET_TO _y = @Evaluate(@round((@Value(_ymax_extent)-@Value(_ymin_extent))/2,0))
    -> DummyVertexCreator
DummyVertexCreator: VertexCreator
    MEASURE_TYPE = Continuous
    MODE_NAME = Replace with Point
    XVAL = @Value(_x)
    YVAL = @Value(_y)
    -> BlankFeatureColorSetter
BlankFeatureColorSetter: FeatureColorSetter
    COLOR = $(Default_Fill_Color)
    FILL_COLOR = $(Default_Fill_Color)
    MODE = Fixed
    COLORED -> ImageRasterizer
