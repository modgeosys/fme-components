FME workspace TestCustomTransformer.fmw
Title: TestCustomTransformer
Description: This template generates a generic regression test driver workspace that can be customized to test the output of a workflow contained within a custom transformer. It includes the transformers 
        AttributeValidationListPopulator 
    and 
        AttributeValidationHTMLReportGenerator 
    to aid in organizing and reporting test results. Regression test driver workspaces can call a target transformer with predefined test data and verify that the results are correct and can be generated without error for both common and edge cases.
For issues or questions, please Create an issue 
        here 
    . For the source, including test driver components, please see the 
        Github repository 
    .
Copyright © 2019-2020 by Modern geoSystems, released under 
        this BSD 3-clause license 
    .
Usage: To use this template, simply:
    Open the template file and save it as a workspace; 
    Modify it to suit your needs, including test preparation, execution, and results validation.
The workflow to be tested should be contained in a custom transformer that is either embedded or linked. This is good design practice anyway, and aids in testing the same workflow with different inputs.
History: 2020-03-11,Kevin Weller,Initial publication.,2022-03-28,Kevin Weller,Upgrade referenced AttributeValidationHTMLReportGenerator to the latest version (9).,2022-03-30,Kevin Weller,Upgrade referenced AttributeValidationHTMLReportGenerator to the latest version (10).,2022-10-17,Kevin Weller,Upgrade referenced AttributeValidationHTMLReportGenerator to the latest version (11).

Parameters:
- BadFeature_Latitude =
- BadFeature_Longitude =
- BadFeature_MultiLineText =
- BadFeature_Number =
- BadFeature_Text =
- EmptyFeature_Latitude =
- EmptyFeature_Longitude =
- EmptyFeature_MultiLineText =
- EmptyFeature_Number =
- EmptyFeature_Text =
- FME_SHAREDRESOURCE_DATA = Resources/Data
- FME_SHAREDRESOURCE_TEMP = Resources/Temp
- GoodFeature_Latitude =
- GoodFeature_Longitude =
- GoodFeature_MultiLineText =
- GoodFeature_Number =
- GoodFeature_Text =

TestStatusAttributeFilter: AttributeFilter
    ATTR_NAME = _test_status
    ATTR_VALUES = <Empty>,<Missing>,<Null>,<Unfiltered>,SUCCEEDED,FAILED
    FAILED -> Terminator
Terminator
    MESSAGE = Test Failure

Bookmark: Create test features.
Note: Create mock feature to test adding a valid feature to the database.
GoodFeatureCreator: Creator
    GEOMTYPE = Geometry Object
    NUM = 1
    CREATED -> GoodFeaturePreparer
Note: Create mock feature to test adding an invalid feature to the database.
BadFeatureCreator: Creator
    GEOMTYPE = Geometry Object
    NUM = 1
    CREATED -> BadFeaturePreparer
Note: Create mock feature to test adding an empty feature to the database.
EmptyFeatureCreator: Creator
    GEOMTYPE = Geometry Object
    NUM = 1
    CREATED -> EmptyFeaturePreparer

Bookmark: Prepare to execute test transformer.
GoodFeaturePreparer: FeaturePreparer
    Feature_Latitude = $(GoodFeature_Latitude)
    Feature_Longitude = $(GoodFeature_Longitude)
    Feature_MultiLineText = $(GoodFeature_MultiLineText)
    Feature_Number = $(GoodFeature_Number)
    Feature_Text = $(GoodFeature_Text)
    -> GoodFeatureCustomTransformer
BadFeaturePreparer: FeaturePreparer
    Feature_Latitude = $(BadFeature_Latitude)
    Feature_Longitude = $(BadFeature_Longitude)
    Feature_MultiLineText = $(BadFeature_MultiLineText)
    Feature_Number = $(BadFeature_Number)
    Feature_Text = $(BadFeature_Text)
    -> BadFeatureCustomTransformer
EmptyFeaturePreparer: FeaturePreparer
    Feature_Latitude = $(EmptyFeature_Latitude)
    Feature_Longitude = $(EmptyFeature_Longitude)
    Feature_MultiLineText = $(EmptyFeature_MultiLineText)
    Feature_Number = $(EmptyFeature_Number)
    Feature_Text = $(EmptyFeature_Text)
    -> EmptyFeatureCustomTransformer

Bookmark: Execute test transformer.
GoodFeatureCustomTransformer: CustomTransformer
    LATITUDE = @Value(latitude)
    LONGITUDE = @Value(longitude)
    MULTILINETEXT = @Value(multilinetext)
    NUMBER = @Value(number)
    TEXT = @Value(text)
    Feature -> GoodFeatureOutputVerifier
    <INVALID> -> GoodFeatureOutputVerifier
BadFeatureCustomTransformer: CustomTransformer
    LATITUDE = @Value(latitude)
    LONGITUDE = @Value(longitude)
    MULTILINETEXT = @Value(multilinetext)
    NUMBER = @Value(number)
    TEXT = @Value(text)
    Feature -> BadFeatureOutputVerifier
    <INVALID> -> BadFeatureOutputVerifier
EmptyFeatureCustomTransformer: CustomTransformer
    LATITUDE = @Value(latitude)
    LONGITUDE = @Value(longitude)
    MULTILINETEXT = @Value(multilinetext)
    NUMBER = @Value(number)
    TEXT = @Value(text)
    Feature -> EmptyFeatureOutputVerifier
    <INVALID> -> EmptyFeatureOutputVerifier

Bookmark: Verify results against expected.
GoodFeatureOutputVerifier
    FME_FEATURE_TYPE = @Value(fme_feature_type)
    GoodFeature_Latitude = $(GoodFeature_Latitude)
    GoodFeature_Longitude = $(GoodFeature_Longitude)
    GoodFeature_MultiLineText = $(GoodFeature_MultiLineText)
    GoodFeature_Number = $(GoodFeature_Number)
    GoodFeature_Text = $(GoodFeature_Text)
    LATITUDE = @Value(latitude)
    LIST_NAME = _fme_validation_message_list{}
    LONGITUDE = @Value(longitude)
    MULTILINETEXT = @Value(multilinetext)
    NUMBER = @Value(number)
    TEXT = @Value(text)
    _FME_VALIDATION_MESSAGE = @Value(_fme_validation_message)
    -> AttributeValidationHTMLReportGenerator
BadFeatureOutputVerifier
    LATITUDE = @Value(latitude)
    LIST_NAME = _fme_validation_message_list{}
    LONGITUDE = @Value(longitude)
    MULTILINETEXT = @Value(multilinetext)
    NUMBER = @Value(number)
    TEXT = @Value(text)
    -> AttributeValidationHTMLReportGenerator
EmptyFeatureOutputVerifier
    LATITUDE = @Value(latitude)
    LIST_NAME = _fme_validation_message_list{}
    LONGITUDE = @Value(longitude)
    MULTILINETEXT = @Value(multilinetext)
    NUMBER = @Value(number)
    TEXT = @Value(text)
    -> AttributeValidationHTMLReportGenerator

Bookmark: Generate & write validation report.
AttributeValidationHTMLReportGenerator
    _FEATURE_ID = id
    -> ReportFeatureWriter [HTML]
ReportFeatureWriter: FeatureWriter
    DATASET = $(FME_SHAREDRESOURCE_TEMP)/CustomTransformerTestOutput.html
    DATASET_ATTR = _dataset
    FEATURE_TYPE_LIST_ATTR = _feature_types
    FORMAT = HTML
    HTML_COORDINATE_SYSTEM_GRANULARITY = FEATURE
    HTML_DESTINATION_DATASETTYPE_VALIDATION = Yes
    HTML_ENCODING = UTF8
    HTML_END_OF_LINE = System
    HTML_MIME_TYPE = text/html
    HTML_OVERWRITE_FILE = YES
    HTML_WRITE_LAST_EOL = YES
    HTML_WRITE_UTF8_BOM = YES
    TOTAL_FEATURES_WRITTEN_ATTR = _total_features_written
    HTML -> TestStatusAttributeFilter

FME custom transformer GoodFeatureOutputVerifier
Verify transformer output after feeding with a good bike rack feature.

Parameters:
- FME_FEATURE_TYPE =
- GoodFeature_Latitude =
- GoodFeature_Longitude =
- GoodFeature_MultiLineText =
- GoodFeature_Number =
- GoodFeature_Text =
- LATITUDE =
- LIST_NAME =
- LONGITUDE =
- MULTILINETEXT =
- NUMBER =
- TEXT =
- _FME_VALIDATION_MESSAGE =

Input (input)
    -> ValidationErrorListElementCounter
ValidationErrorListElementCounter: ListElementCounter
    CNT_ATTR = _validation_list_length
    LIST_NAME = $(LIST_NAME)
    -> TestValidationErrorMessageListsAttributeRemover
TestValidationErrorMessageListsAttributeRemover: AttributeRemover
    LIST_ATTRS = $(LIST_NAME)
    -> AttributeValidator
AttributeValidator
    TABLE = _validation_list_length;RANGE;[0,0]/text;IN;$(GoodFeature_Text)/multilinetext;IN;$(GoodFeature_MultiLineText)/number;IN;$(GoodFeature_Number)/longitude;IN;$(GoodFeature_Longitude)/latitude;IN;$(GoodFeature_Latitude)
    PASSED -> AttributeValidationListPopulator
    FAILED -> AttributeValidationListPopulator
AttributeValidationListPopulator
    Validator_Name = GoodFeatureOutputVerifier
    -> Output (output)
Output (output)

FME custom transformer CustomTransformer

Parameters:
- LATITUDE =
- LONGITUDE =
- MULTILINETEXT =
- NUMBER =
- TEXT =

Input (input)
    -> AttributeValidator
AttributeValidator
    TABLE = number;RANGE;[1,100]/longitude;RANGE;[-180,180]/latitude;RANGE;[-90,90]/text,multilinetext;MINIMUM_LENGTH;2/text;MAXIMUM_LENGTH;40
    PASSED -> ListPopulator
    FAILED -> AttributeValidationListPopulator
ListPopulator
    LIST_NAME = _fme_validation_message_list
    PREFIX = nothing
    -> VertexCreator
VertexCreator
    IGNORE_DUPLICATES = Yes
    MEASURE_TYPE = Continuous
    MISSING_VAL_MODE = None (Drop Values)
    MODE_NAME = Add Point
    XVAL = @Value(longitude)
    YVAL = @Value(latitude)
    -> CoordinateSystemSetter
CoordinateSystemSetter
    COORDSYS = EPSG:4326
    -> AttributeRemover
AttributeRemover
    REMOVE_ATTRS = longitude,latitude
    -> CoordinateExtractor
CoordinateExtractor
    IND = 0
    MODE = Specify Coordinate
    X_ATTR = longitude
    Y_ATTR = latitude
    -> Feature (output)
Feature (output)
AttributeValidationListPopulator
    Validator_Name = CustomTransformer
    -> <INVALID> (output)
<INVALID> (output)

FME custom transformer AttributeValidationListPopulator
Enhance the output from a standard AttributeValidator transformer with contextual information to assist subsequent diagnosis of invalid attribute values.  The output is meant to be used by a subsequent AttributeValidationHTMLReportGenerator to create a human-readable report of invalid attributes at different positions within a calling workspace or custom transformer.
IMPORTANT: This transformer must be embedded, not linked, for the calling module (workspace or linked custom transformer) to be properly identified; this is the default when you add it to your workflow.
This transformer is part of a suite that can be used for both data and workflow quality.  For the former, data can be tested and exception reports generated from inside any workspace or transformer.  For the latter, regression test driver workspaces can call a target workspace or transformer with predefined test data and verify that the results are correct and can be generated without error for both common and edge cases.
For issues or questions, please Create an issue here.  For the source, including test driver components, please see the Github repository.
Copyright © 2019-2020 by Modern geoSystems, released under this BSD 3-clause license.
Ports
Input
Feed all features that have just been tested with a standard AttributeValidator transformer.
Output
The input feature enhanced with the following list attributes:
_fme_validation_message_list{}.validator_name - The name or prefix of the AttributeValidator, as provided in the Validator_Name parameter, that detected the error with the corresponding element in _fme_validation_message_list{}
_fme_validation_message_list{}.calling_module - The name of the workspace or linked custom transformer where the named validator exists
Parameters
Specify the required yet unknown values for the preceding AttributeValidator.
Validator_Name
The name or prefix of the preceding AttributeValidator.

Parameters:
- Validator_Name =

Input (input)
    -> ParameterFetcher
ParameterFetcher
    ATTR_LIST = _FME_MF_DIR $(FME_MF_DIR_USERTYPED) _FME_MF_NAME $(FME_MF_NAME)
    -> AttributeCreator
AttributeCreator
    ATTR_TABLE:
      SET_TO _mgs_calling_module = @Value(_FME_MF_DIR)@Value(_FME_MF_NAME)
      SET_TO _mgs_validator_name = $(Validator_Name)
    -> PythonCaller
PythonCaller
    NEW_ATTRIBUTES = _fme_validation_message_list{}.validator_name _fme_validation_message_list{}.calling_module
    PYTHONSOURCE:
      import fme
      import fmeobjects

      def processFeature(feature):
          messages = feature.getAttribute('_fme_validation_message_list')
          if messages:
              index = 0
              for message in messages:
                  if feature.getAttributeNullMissingAndType('_fme_validation_message_list{' + str(index) + '}.validator_name')[1]:
                      feature.setAttribute('_fme_validation_message_list{' + str(index) + '}.validator_name', feature.getAttribute('_mgs_validator_name'))
                      feature.setAttribute('_fme_validation_message_list{' + str(index) + '}.calling_module', feature.getAttribute('_mgs_calling_module'))
                  index += 1
    PYTHONSYMBOL = processFeature
    -> AttributeExposer
AttributeExposer
    ATTR_LIST = _fme_validation_message
    -> AttributeRemover_2
AttributeRemover_2
    REMOVE_ATTRS = _mgs_validator_name,_fme_validation_message,_FME_MF_DIR,_FME_MF_NAME,_mgs_calling_module
    -> Output (output)
Output (output)

FME custom transformer EmptyFeatureOutputVerifier
Verify transformer output after feeding with an empty bike rack feature.

Parameters:
- LATITUDE =
- LIST_NAME =
- LONGITUDE =
- MULTILINETEXT =
- NUMBER =
- TEXT =

Input (input)
    -> ValidationErrorListElementCounter
ValidationErrorListElementCounter: ListElementCounter
    CNT_ATTR = _validation_list_length
    LIST_NAME = $(LIST_NAME)
    -> TestValidationErrorMessageListsAttributeRemover
TestValidationErrorMessageListsAttributeRemover: AttributeRemover
    LIST_ATTRS = _fme_validation_message_list{} _fme_validation_message_list{}.calling_module _fme_validation_message_list{}.validator_name
    -> ValidationErrorListAttributeValidator
ValidationErrorListAttributeValidator: AttributeValidator
    TABLE = _validation_list_length;RANGE;[5,5]
    PASSED -> AttributeValidationListPopulator
    FAILED -> AttributeValidationListPopulator
AttributeValidationListPopulator
    Validator_Name = EmptyFeatureOutputVerifier
    -> Output (output)
Output (output)

FME custom transformer BadFeatureOutputVerifier
Verify transformer output after feeding with a bad bike rack feature.

Parameters:
- LATITUDE =
- LIST_NAME =
- LONGITUDE =
- MULTILINETEXT =
- NUMBER =
- TEXT =

Input (input)
    -> ValidationErrorListElementCounter
ValidationErrorListElementCounter: ListElementCounter
    CNT_ATTR = _validation_list_length
    LIST_NAME = $(LIST_NAME)
    -> TestValidationErrorMessageListsAttributeRemover
TestValidationErrorMessageListsAttributeRemover: AttributeRemover
    LIST_ATTRS = _fme_validation_message_list{} _fme_validation_message_list{}.calling_module _fme_validation_message_list{}.validator_name
    -> ValidationErrorListAttributeValidator
ValidationErrorListAttributeValidator: AttributeValidator
    TABLE = _validation_list_length;RANGE;[4,4]
    PASSED -> AttributeValidationListPopulator
    FAILED -> AttributeValidationListPopulator
AttributeValidationListPopulator
    Validator_Name = BadFeatureOutputVerifier
    -> Output (output)
Output (output)

FME custom transformer FeaturePreparer

Parameters:
- Feature_Latitude =
- Feature_Longitude =
- Feature_MultiLineText =
- Feature_Number =
- Feature_Text =

Input (input)
    -> ParameterFetcher
ParameterFetcher
    ATTR_LIST = text $(Feature_Text) multilinetext $(Feature_MultiLineText) number $(Feature_Number) longitude $(Feature_Longitude) latitude $(Feature_Latitude)
    -> AttributeCreator
AttributeCreator
    ATTR_TABLE = SET_TO fme_feature_type = sample_feature
    -> Output (output)
Output (output)
